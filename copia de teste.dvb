Attribute VB_Name = "Contagem"
Public aContagem() As String
Sub Preenche_Cabo()

Dim iNumero_Inicial As Long
Dim iNumero_Final As Long
Dim bSelecao As Boolean

sTecla_direita = False
sRamal = InputBox("Numero da Ramal:")
'If sSP <> "" Then
'    initializeaContagem
'    iAcon = sSP - 1
'    sContagem = aContagem(iAcon)
'End If
sContagem = InputBox("Contagem: ")



aContagem = Split(sContagem, "-")
iNumero_Inicial = aContagem(0)
iNumero_Final = aContagem(1)
bSelecao = True
While bSelecao = True
    sSelecao = Format(Now(), "hh:mm:ss")
    'ThisDrawing.
    Set ssetObj = ThisDrawing.SelectionSets.Add(sSelecao & "_")
    ssetObj.SelectOnScreen
      
    
    If ssetObj.Count > 0 Then
        If ssetObj.Item(0).ObjectName = "AcDbBlockReference" Then
        ' Get the attributes for the block reference
        
            Dim varAttributes As Variant
            varAttributes = ssetObj.Item(0).GetAttributes
            
                For II = 0 To UBound(varAttributes)
                    
                        If UCase(varAttributes(II).TagString) = UCase("TR") Then
                            'Stop
                            If sTecla_direita = True Then
                                iNumero_Final = iNumero_Final - 1
                                sTecla_direita = False
                            End If
                            ' copiar essa parte
                            sNumero_Inicial = "0000" & iNumero_Inicial
                            sNumero_Final = "0000" & iNumero_Final
                            
                            If iNumero_Inicial > 999 Then
                                sNumero_Inicial = Right(sNumero_Inicial, 4)
                            ElseIf iNumero_Inicial > 99 Then
                                sNumero_Inicial = Right(sNumero_Inicial, 3)
                            ElseIf iNumero_Inicial > 9 Then
                                sNumero_Inicial = Right(sNumero_Inicial, 2)
                            Else
                                sNumero_Inicial = Right(sNumero_Inicial, 2)
                            End If
                                
                            
                            If iNumero_Final > 999 Then
                                sNumero_Final = Right(sNumero_Final, 4)
                            ElseIf iNumero_Final > 99 Then
                                sNumero_Final = Right(sNumero_Final, 3)
                            ElseIf iNumero_Final > 9 Then
                                sNumero_Final = Right(sNumero_Final, 2)
                            Else
                                sNumero_Final = Right(sNumero_Final, 2)
                            End If
                                
                            ' até aqui
                            
                            If iNumero_Inicial = iNumero_Final Then
                                varAttributes(II).TextString = "TR02,F" & sRamal & "/" & sNumero_Inicial
                            Else
                                varAttributes(II).TextString = "TR02,F" & sRamal & "/" & sNumero_Inicial & "-" & sNumero_Final
                            End If
                   
                        End If
                Next
        End If
        ThisDrawing.Regen acActiveViewport
        
        iNumero_Final = iNumero_Final + 1
        Set ssetObj = Nothing
    Else
        bSelecao = False
    End If
Wend
   
 
End Sub
Function initializeaContagem()

ReDim aContagem(0 To 864)

aContagem(0) = "01-08"
aContagem(1) = "09-16"
aContagem(2) = "17-24"
aContagem(3) = "25-32"
aContagem(4) = "33-40"
aContagem(5) = "41-48"
aContagem(6) = "49-56"
aContagem(7) = "57-64"
aContagem(8) = "65-72"
aContagem(9) = "73-80"
aContagem(10) = "81-88"
aContagem(11) = "89-96"
aContagem(12) = "97-104"
aContagem(13) = "105-112"
aContagem(14) = "113-120"
aContagem(15) = "121-128"
aContagem(16) = "129-136"
aContagem(17) = "137-144"
aContagem(18) = "145-152"
aContagem(19) = "153-160"
aContagem(20) = "161-168"
aContagem(21) = "169-176"
aContagem(22) = "177-184"
aContagem(23) = "185-192"
aContagem(24) = "193-200"
aContagem(25) = "201-208"
aContagem(26) = "209-216"
aContagem(27) = "217-224"
aContagem(28) = "225-232"
aContagem(29) = "233-240"
aContagem(30) = "241-248"
aContagem(31) = "249-256"
aContagem(32) = "257-264"
aContagem(33) = "265-272"
aContagem(34) = "273-280"
aContagem(35) = "281-288"
aContagem(36) = "289-296"
aContagem(37) = "297-304"
aContagem(38) = "305-312"
aContagem(39) = "313-320"
aContagem(40) = "321-328"
aContagem(41) = "329-336"
aContagem(42) = "337-344"
aContagem(43) = "345-352"
aContagem(44) = "353-360"
aContagem(45) = "361-368"
aContagem(46) = "369-376"
aContagem(47) = "377-384"
aContagem(48) = "385-392"
aContagem(49) = "393-400"
aContagem(50) = "401-408"
aContagem(51) = "409-416"
aContagem(52) = "417-424"
aContagem(53) = "425-432"
aContagem(54) = "433-440"
aContagem(55) = "441-448"
aContagem(56) = "449-456"
aContagem(57) = "457-464"
aContagem(58) = "465-472"
aContagem(59) = "473-480"
aContagem(60) = "481-488"
aContagem(61) = "489-496"
aContagem(62) = "497-504"
aContagem(63) = "505-512"
aContagem(64) = "513-520"
aContagem(65) = "521-528"
aContagem(66) = "529-536"
aContagem(67) = "537-544"
aContagem(68) = "545-552"
aContagem(69) = "553-560"
aContagem(70) = "561-568"
aContagem(71) = "569-576"
aContagem(72) = "577-584"
aContagem(73) = "585-592"
aContagem(74) = "593-600"
aContagem(75) = "601-608"
aContagem(76) = "609-616"
aContagem(77) = "617-624"
aContagem(78) = "625-632"
aContagem(79) = "633-640"
aContagem(80) = "641-648"
aContagem(81) = "649-656"
aContagem(82) = "657-664"
aContagem(83) = "665-672"
aContagem(84) = "673-680"
aContagem(85) = "681-688"
aContagem(86) = "689-696"
aContagem(87) = "697-704"
aContagem(88) = "705-712"
aContagem(89) = "713-720"
aContagem(90) = "721-728"
aContagem(91) = "729-736"
aContagem(92) = "737-744"
aContagem(93) = "745-752"
aContagem(94) = "753-760"
aContagem(95) = "761-768"
aContagem(96) = "769-776"
aContagem(97) = "777-784"
aContagem(98) = "785-792"
aContagem(99) = "793-800"
aContagem(100) = "801-808"
aContagem(101) = "809-816"
aContagem(102) = "817-824"
aContagem(103) = "825-832"
aContagem(104) = "833-840"
aContagem(105) = "841-848"
aContagem(106) = "849-856"
aContagem(107) = "857-864"
aContagem(108) = "865-872"
aContagem(109) = "873-880"
aContagem(110) = "881-888"
aContagem(111) = "889-896"
aContagem(112) = "897-904"
aContagem(113) = "905-912"
aContagem(114) = "913-920"
aContagem(115) = "921-928"
aContagem(116) = "929-936"
aContagem(117) = "937-944"
aContagem(118) = "945-952"
aContagem(119) = "953-960"
aContagem(120) = "961-968"
aContagem(121) = "969-976"
aContagem(122) = "977-984"
aContagem(123) = "985-992"
aContagem(124) = "993-1000"
aContagem(125) = "1001-1008"
aContagem(126) = "1009-1016"
aContagem(127) = "1017-1024"
aContagem(128) = "1025-1032"
aContagem(129) = "1033-1040"
aContagem(130) = "1041-1048"
aContagem(131) = "1049-1056"
aContagem(132) = "1057-1064"
aContagem(133) = "1065-1072"
aContagem(134) = "1073-1080"
aContagem(135) = "1081-1088"
aContagem(136) = "1089-1096"
aContagem(137) = "1097-1104"
aContagem(138) = "1105-1112"
aContagem(139) = "1113-1120"
aContagem(140) = "1121-1128"
aContagem(141) = "1129-1136"
aContagem(142) = "1137-1144"
aContagem(143) = "1145-1152"
aContagem(144) = "1153-1160"
aContagem(145) = "1161-1168"
aContagem(146) = "1169-1176"
aContagem(147) = "1177-1184"
aContagem(148) = "1185-1192"
aContagem(149) = "1193-1200"
aContagem(150) = "1201-1208"
aContagem(151) = "1209-1216"
aContagem(152) = "1217-1224"
aContagem(153) = "1225-1232"
aContagem(154) = "1233-1240"
aContagem(155) = "1241-1248"
aContagem(156) = "1249-1256"
aContagem(157) = "1257-1264"
aContagem(158) = "1265-1272"
aContagem(159) = "1273-1280"
aContagem(160) = "1281-1288"
aContagem(161) = "1289-1296"
aContagem(162) = "1297-1304"
aContagem(163) = "1305-1312"
aContagem(164) = "1313-1320"
aContagem(165) = "1321-1328"
aContagem(166) = "1329-1336"
aContagem(167) = "1337-1344"
aContagem(168) = "1345-1352"
aContagem(169) = "1353-1360"
aContagem(170) = "1361-1368"
aContagem(171) = "1369-1376"
aContagem(172) = "1377-1384"
aContagem(173) = "1385-1392"
aContagem(174) = "1393-1400"
aContagem(175) = "1401-1408"
aContagem(176) = "1409-1416"
aContagem(177) = "1417-1424"
aContagem(178) = "1425-1432"
aContagem(179) = "1433-1440"
aContagem(180) = "1441-1448"
aContagem(181) = "1449-1456"
aContagem(182) = "1457-1464"
aContagem(183) = "1465-1472"
aContagem(184) = "1473-1480"
aContagem(185) = "1481-1488"
aContagem(186) = "1489-1496"
aContagem(187) = "1497-1504"
aContagem(188) = "1505-1512"
aContagem(189) = "1513-1520"
aContagem(190) = "1521-1528"
aContagem(191) = "1529-1536"
aContagem(192) = "1537-1544"
aContagem(193) = "1545-1552"
aContagem(194) = "1553-1560"
aContagem(195) = "1561-1568"
aContagem(196) = "1569-1576"
aContagem(197) = "1577-1584"
aContagem(198) = "1585-1592"
aContagem(199) = "1593-1600"
aContagem(200) = "1601-1608"
aContagem(201) = "1609-1616"
aContagem(202) = "1617-1624"
aContagem(203) = "1625-1632"
aContagem(204) = "1633-1640"
aContagem(205) = "1641-1648"
aContagem(206) = "1649-1656"
aContagem(207) = "1657-1664"
aContagem(208) = "1665-1672"
aContagem(209) = "1673-1680"
aContagem(210) = "1681-1688"
aContagem(211) = "1689-1696"
aContagem(212) = "1697-1704"
aContagem(213) = "1705-1712"
aContagem(214) = "1713-1720"
aContagem(215) = "1721-1728"
aContagem(216) = "1729-1736"
aContagem(217) = "1737-1744"
aContagem(218) = "1745-1752"
aContagem(219) = "1753-1760"
aContagem(220) = "1761-1768"
aContagem(221) = "1769-1776"
aContagem(222) = "1777-1784"
aContagem(223) = "1785-1792"
aContagem(224) = "1793-1800"
aContagem(225) = "1801-1808"
aContagem(226) = "1809-1816"
aContagem(227) = "1817-1824"
aContagem(228) = "1825-1832"
aContagem(229) = "1833-1840"
aContagem(230) = "1841-1848"
aContagem(231) = "1849-1856"
aContagem(232) = "1857-1864"
aContagem(233) = "1865-1872"
aContagem(234) = "1873-1880"
aContagem(235) = "1881-1888"
aContagem(236) = "1889-1896"
aContagem(237) = "1897-1904"
aContagem(238) = "1905-1912"
aContagem(239) = "1913-1920"
aContagem(240) = "1921-1928"
aContagem(241) = "1929-1936"
aContagem(242) = "1937-1944"
aContagem(243) = "1945-1952"
aContagem(244) = "1953-1960"
aContagem(245) = "1961-1968"
aContagem(246) = "1969-1976"
aContagem(247) = "1977-1984"
aContagem(248) = "1985-1992"
aContagem(249) = "1993-2000"
aContagem(250) = "2001-2008"
aContagem(251) = "2009-2016"
aContagem(252) = "2017-2024"
aContagem(253) = "2025-2032"
aContagem(254) = "2033-2040"
aContagem(255) = "2041-2048"
aContagem(256) = "2049-2056"
aContagem(257) = "2057-2064"
aContagem(258) = "2065-2072"
aContagem(259) = "2073-2080"
aContagem(260) = "2081-2088"
aContagem(261) = "2089-2096"
aContagem(262) = "2097-2104"
aContagem(263) = "2105-2112"
aContagem(264) = "2113-2120"
aContagem(265) = "2121-2128"
aContagem(266) = "2129-2136"
aContagem(267) = "2137-2144"
aContagem(268) = "2145-2152"
aContagem(269) = "2153-2160"
aContagem(270) = "2161-2168"
aContagem(271) = "2169-2176"
aContagem(272) = "2177-2184"
aContagem(273) = "2185-2192"
aContagem(274) = "2193-2200"
aContagem(275) = "2201-2208"
aContagem(276) = "2209-2216"
aContagem(277) = "2217-2224"
aContagem(278) = "2225-2232"
aContagem(279) = "2233-2240"
aContagem(280) = "2241-2248"
aContagem(281) = "2249-2256"
aContagem(282) = "2257-2264"
aContagem(283) = "2265-2272"
aContagem(284) = "2273-2280"
aContagem(285) = "2281-2288"
aContagem(286) = "2289-2296"
aContagem(287) = "2297-2304"
aContagem(288) = "2305-2312"
aContagem(289) = "2313-2320"
aContagem(290) = "2321-2328"
aContagem(291) = "2329-2336"
aContagem(292) = "2337-2344"
aContagem(293) = "2345-2352"
aContagem(294) = "2353-2360"
aContagem(295) = "2361-2368"
aContagem(296) = "2369-2376"
aContagem(297) = "2377-2384"
aContagem(298) = "2385-2392"
aContagem(299) = "2393-2400"
aContagem(300) = "2401-2408"
aContagem(301) = "2409-2416"
aContagem(302) = "2417-2424"
aContagem(303) = "2425-2432"
aContagem(304) = "2433-2440"
aContagem(305) = "2441-2448"
aContagem(306) = "2449-2456"
aContagem(307) = "2457-2464"
aContagem(308) = "2465-2472"
aContagem(309) = "2473-2480"
aContagem(310) = "2481-2488"
aContagem(311) = "2489-2496"
aContagem(312) = "2497-2504"
aContagem(313) = "2505-2512"
aContagem(314) = "2513-2520"
aContagem(315) = "2521-2528"
aContagem(316) = "2529-2536"
aContagem(317) = "2537-2544"
aContagem(318) = "2545-2552"
aContagem(319) = "2553-2560"
aContagem(320) = "2561-2568"
aContagem(321) = "2569-2576"
aContagem(322) = "2577-2584"
aContagem(323) = "2585-2592"
aContagem(324) = "2593-2600"
aContagem(325) = "2601-2608"
aContagem(326) = "2609-2616"
aContagem(327) = "2617-2624"
aContagem(328) = "2625-2632"
aContagem(329) = "2633-2640"
aContagem(330) = "2641-2648"
aContagem(331) = "2649-2656"
aContagem(332) = "2657-2664"
aContagem(333) = "2665-2672"
aContagem(334) = "2673-2680"
aContagem(335) = "2681-2688"
aContagem(336) = "2689-2696"
aContagem(337) = "2697-2704"
aContagem(338) = "2705-2712"
aContagem(339) = "2713-2720"
aContagem(340) = "2721-2728"
aContagem(341) = "2729-2736"
aContagem(342) = "2737-2744"
aContagem(343) = "2745-2752"
aContagem(344) = "2753-2760"
aContagem(345) = "2761-2768"
aContagem(346) = "2769-2776"
aContagem(347) = "2777-2784"
aContagem(348) = "2785-2792"
aContagem(349) = "2793-2800"
aContagem(350) = "2801-2808"
aContagem(351) = "2809-2816"
aContagem(352) = "2817-2824"
aContagem(353) = "2825-2832"
aContagem(354) = "2833-2840"
aContagem(355) = "2841-2848"
aContagem(356) = "2849-2856"
aContagem(357) = "2857-2864"
aContagem(358) = "2865-2872"
aContagem(359) = "2873-2880"
aContagem(360) = "2881-2888"
aContagem(361) = "2889-2896"
aContagem(362) = "2897-2904"
aContagem(363) = "2905-2912"
aContagem(364) = "2913-2920"
aContagem(365) = "2921-2928"
aContagem(366) = "2929-2936"
aContagem(367) = "2937-2944"
aContagem(368) = "2945-2952"
aContagem(369) = "2953-2960"
aContagem(370) = "2961-2968"
aContagem(371) = "2969-2976"
aContagem(372) = "2977-2984"
aContagem(373) = "2985-2992"
aContagem(374) = "2993-3000"
aContagem(375) = "3001-3008"
aContagem(376) = "3009-3016"
aContagem(377) = "3017-3024"
aContagem(378) = "3025-3032"
aContagem(379) = "3033-3040"
aContagem(380) = "3041-3048"
aContagem(381) = "3049-3056"
aContagem(382) = "3057-3064"
aContagem(383) = "3065-3072"
aContagem(384) = "3073-3080"
aContagem(385) = "3081-3088"
aContagem(386) = "3089-3096"
aContagem(387) = "3097-3104"
aContagem(388) = "3105-3112"
aContagem(389) = "3113-3120"
aContagem(390) = "3121-3128"
aContagem(391) = "3129-3136"
aContagem(392) = "3137-3144"
aContagem(393) = "3145-3152"
aContagem(394) = "3153-3160"
aContagem(395) = "3161-3168"
aContagem(396) = "3169-3176"
aContagem(397) = "3177-3184"
aContagem(398) = "3185-3192"
aContagem(399) = "3193-3200"
aContagem(400) = "3201-3208"
aContagem(401) = "3209-3216"
aContagem(402) = "3217-3224"
aContagem(403) = "3225-3232"
aContagem(404) = "3233-3240"
aContagem(405) = "3241-3248"
aContagem(406) = "3249-3256"
aContagem(407) = "3257-3264"
aContagem(408) = "3265-3272"
aContagem(409) = "3273-3280"
aContagem(410) = "3281-3288"
aContagem(411) = "3289-3296"
aContagem(412) = "3297-3304"
aContagem(413) = "3305-3312"
aContagem(414) = "3313-3320"
aContagem(415) = "3321-3328"
aContagem(416) = "3329-3336"
aContagem(417) = "3337-3344"
aContagem(418) = "3345-3352"
aContagem(419) = "3353-3360"
aContagem(420) = "3361-3368"
aContagem(421) = "3369-3376"
aContagem(422) = "3377-3384"
aContagem(423) = "3385-3392"
aContagem(424) = "3393-3400"
aContagem(425) = "3401-3408"
aContagem(426) = "3409-3416"
aContagem(427) = "3417-3424"
aContagem(428) = "3425-3432"
aContagem(429) = "3433-3440"
aContagem(430) = "3441-3448"
aContagem(431) = "3449-3456"
aContagem(432) = "3457-3464"
aContagem(433) = "3465-3472"
aContagem(434) = "3473-3480"
aContagem(435) = "3481-3488"
aContagem(436) = "3489-3496"
aContagem(437) = "3497-3504"
aContagem(438) = "3505-3512"
aContagem(439) = "3513-3520"
aContagem(440) = "3521-3528"
aContagem(441) = "3529-3536"
aContagem(442) = "3537-3544"
aContagem(443) = "3545-3552"
aContagem(444) = "3553-3560"
aContagem(445) = "3561-3568"
aContagem(446) = "3569-3576"
aContagem(447) = "3577-3584"
aContagem(448) = "3585-3592"
aContagem(449) = "3593-3600"
aContagem(450) = "3601-3608"
aContagem(451) = "3609-3616"
aContagem(452) = "3617-3624"
aContagem(453) = "3625-3632"
aContagem(454) = "3633-3640"
aContagem(455) = "3641-3648"
aContagem(456) = "3649-3656"
aContagem(457) = "3657-3664"
aContagem(458) = "3665-3672"
aContagem(459) = "3673-3680"
aContagem(460) = "3681-3688"
aContagem(461) = "3689-3696"
aContagem(462) = "3697-3704"
aContagem(463) = "3705-3712"
aContagem(464) = "3713-3720"
aContagem(465) = "3721-3728"
aContagem(466) = "3729-3736"
aContagem(467) = "3737-3744"
aContagem(468) = "3745-3752"
aContagem(469) = "3753-3760"
aContagem(470) = "3761-3768"
aContagem(471) = "3769-3776"
aContagem(472) = "3777-3784"
aContagem(473) = "3785-3792"
aContagem(474) = "3793-3800"
aContagem(475) = "3801-3808"
aContagem(476) = "3809-3816"
aContagem(477) = "3817-3824"
aContagem(478) = "3825-3832"
aContagem(479) = "3833-3840"
aContagem(480) = "3841-3848"
aContagem(481) = "3849-3856"
aContagem(482) = "3857-3864"
aContagem(483) = "3865-3872"
aContagem(484) = "3873-3880"
aContagem(485) = "3881-3888"
aContagem(486) = "3889-3896"
aContagem(487) = "3897-3904"
aContagem(488) = "3905-3912"
aContagem(489) = "3913-3920"
aContagem(490) = "3921-3928"
aContagem(491) = "3929-3936"
aContagem(492) = "3937-3944"
aContagem(493) = "3945-3952"
aContagem(494) = "3953-3960"
aContagem(495) = "3961-3968"
aContagem(496) = "3969-3976"
aContagem(497) = "3977-3984"
aContagem(498) = "3985-3992"
aContagem(499) = "3993-4000"
aContagem(500) = "4001-4008"
aContagem(501) = "4009-4016"
aContagem(502) = "4017-4024"
aContagem(503) = "4025-4032"
aContagem(504) = "4033-4040"
aContagem(505) = "4041-4048"
aContagem(506) = "4049-4056"
aContagem(507) = "4057-4064"
aContagem(508) = "4065-4072"
aContagem(509) = "4073-4080"
aContagem(510) = "4081-4088"
aContagem(511) = "4089-4096"
aContagem(512) = "4097-4104"
aContagem(513) = "4105-4112"
aContagem(514) = "4113-4120"
aContagem(515) = "4121-4128"
aContagem(516) = "4129-4136"
aContagem(517) = "4137-4144"
aContagem(518) = "4145-4152"
aContagem(519) = "4153-4160"
aContagem(520) = "4161-4168"
aContagem(521) = "4169-4176"
aContagem(522) = "4177-4184"
aContagem(523) = "4185-4192"
aContagem(524) = "4193-4200"
aContagem(525) = "4201-4208"
aContagem(526) = "4209-4216"
aContagem(527) = "4217-4224"
aContagem(528) = "4225-4232"
aContagem(529) = "4233-4240"
aContagem(530) = "4241-4248"
aContagem(531) = "4249-4256"
aContagem(532) = "4257-4264"
aContagem(533) = "4265-4272"
aContagem(534) = "4273-4280"
aContagem(535) = "4281-4288"
aContagem(536) = "4289-4296"
aContagem(537) = "4297-4304"
aContagem(538) = "4305-4312"
aContagem(539) = "4313-4320"
aContagem(540) = "4321-4328"
aContagem(541) = "4329-4336"
aContagem(542) = "4337-4344"
aContagem(543) = "4345-4352"
aContagem(544) = "4353-4360"
aContagem(545) = "4361-4368"
aContagem(546) = "4369-4376"
aContagem(547) = "4377-4384"
aContagem(548) = "4385-4392"
aContagem(549) = "4393-4400"
aContagem(550) = "4401-4408"
aContagem(551) = "4409-4416"
aContagem(552) = "4417-4424"
aContagem(553) = "4425-4432"
aContagem(554) = "4433-4440"
aContagem(555) = "4441-4448"
aContagem(556) = "4449-4456"
aContagem(557) = "4457-4464"
aContagem(558) = "4465-4472"
aContagem(559) = "4473-4480"
aContagem(560) = "4481-4488"
aContagem(561) = "4489-4496"
aContagem(562) = "4497-4504"
aContagem(563) = "4505-4512"
aContagem(564) = "4513-4520"
aContagem(565) = "4521-4528"
aContagem(566) = "4529-4536"
aContagem(567) = "4537-4544"
aContagem(568) = "4545-4552"
aContagem(569) = "4553-4560"
aContagem(570) = "4561-4568"
aContagem(571) = "4569-4576"
aContagem(572) = "4577-4584"
aContagem(573) = "4585-4592"
aContagem(574) = "4593-4600"
aContagem(575) = "4601-4608"
aContagem(576) = "4609-4616"
aContagem(577) = "4617-4624"
aContagem(578) = "4625-4632"
aContagem(579) = "4633-4640"
aContagem(580) = "4641-4648"
aContagem(581) = "4649-4656"
aContagem(582) = "4657-4664"
aContagem(583) = "4665-4672"
aContagem(584) = "4673-4680"
aContagem(585) = "4681-4688"
aContagem(586) = "4689-4696"
aContagem(587) = "4697-4704"
aContagem(588) = "4705-4712"
aContagem(589) = "4713-4720"
aContagem(590) = "4721-4728"
aContagem(591) = "4729-4736"
aContagem(592) = "4737-4744"
aContagem(593) = "4745-4752"
aContagem(594) = "4753-4760"
aContagem(595) = "4761-4768"
aContagem(596) = "4769-4776"
aContagem(597) = "4777-4784"
aContagem(598) = "4785-4792"
aContagem(599) = "4793-4800"
aContagem(600) = "4801-4808"
aContagem(601) = "4809-4816"
aContagem(602) = "4817-4824"
aContagem(603) = "4825-4832"
aContagem(604) = "4833-4840"
aContagem(605) = "4841-4848"
aContagem(606) = "4849-4856"
aContagem(607) = "4857-4864"
aContagem(608) = "4865-4872"
aContagem(609) = "4873-4880"
aContagem(610) = "4881-4888"
aContagem(611) = "4889-4896"
aContagem(612) = "4897-4904"
aContagem(613) = "4905-4912"
aContagem(614) = "4913-4920"
aContagem(615) = "4921-4928"
aContagem(616) = "4929-4936"
aContagem(617) = "4937-4944"
aContagem(618) = "4945-4952"
aContagem(619) = "4953-4960"
aContagem(620) = "4961-4968"
aContagem(621) = "4969-4976"
aContagem(622) = "4977-4984"
aContagem(623) = "4985-4992"
aContagem(624) = "4993-5000"
aContagem(625) = "5001-5008"
aContagem(626) = "5009-5016"
aContagem(627) = "5017-5024"
aContagem(628) = "5025-5032"
aContagem(629) = "5033-5040"
aContagem(630) = "5041-5048"
aContagem(631) = "5049-5056"
aContagem(632) = "5057-5064"
aContagem(633) = "5065-5072"
aContagem(634) = "5073-5080"
aContagem(635) = "5081-5088"
aContagem(636) = "5089-5096"
aContagem(637) = "5097-5104"
aContagem(638) = "5105-5112"
aContagem(639) = "5113-5120"
aContagem(640) = "5121-5128"
aContagem(641) = "5129-5136"
aContagem(642) = "5137-5144"
aContagem(643) = "5145-5152"
aContagem(644) = "5153-5160"
aContagem(645) = "5161-5168"
aContagem(646) = "5169-5176"
aContagem(647) = "5177-5184"
aContagem(648) = "5185-5192"
aContagem(649) = "5193-5200"
aContagem(650) = "5201-5208"
aContagem(651) = "5209-5216"
aContagem(652) = "5217-5224"
aContagem(653) = "5225-5232"
aContagem(654) = "5233-5240"
aContagem(655) = "5241-5248"
aContagem(656) = "5249-5256"
aContagem(657) = "5257-5264"
aContagem(658) = "5265-5272"
aContagem(659) = "5273-5280"
aContagem(660) = "5281-5288"
aContagem(661) = "5289-5296"
aContagem(662) = "5297-5304"
aContagem(663) = "5305-5312"
aContagem(664) = "5313-5320"
aContagem(665) = "5321-5328"
aContagem(666) = "5329-5336"
aContagem(667) = "5337-5344"
aContagem(668) = "5345-5352"
aContagem(669) = "5353-5360"
aContagem(670) = "5361-5368"
aContagem(671) = "5369-5376"
aContagem(672) = "5377-5384"
aContagem(673) = "5385-5392"
aContagem(674) = "5393-5400"
aContagem(675) = "5401-5408"
aContagem(676) = "5409-5416"
aContagem(677) = "5417-5424"
aContagem(678) = "5425-5432"
aContagem(679) = "5433-5440"
aContagem(680) = "5441-5448"
aContagem(681) = "5449-5456"
aContagem(682) = "5457-5464"
aContagem(683) = "5465-5472"
aContagem(684) = "5473-5480"
aContagem(685) = "5481-5488"
aContagem(686) = "5489-5496"
aContagem(687) = "5497-5504"
aContagem(688) = "5505-5512"
aContagem(689) = "5513-5520"
aContagem(690) = "5521-5528"
aContagem(691) = "5529-5536"
aContagem(692) = "5537-5544"
aContagem(693) = "5545-5552"
aContagem(694) = "5553-5560"
aContagem(695) = "5561-5568"
aContagem(696) = "5569-5576"
aContagem(697) = "5577-5584"
aContagem(698) = "5585-5592"
aContagem(699) = "5593-5600"
aContagem(700) = "5601-5608"
aContagem(701) = "5609-5616"
aContagem(702) = "5617-5624"
aContagem(703) = "5625-5632"
aContagem(704) = "5633-5640"
aContagem(705) = "5641-5648"
aContagem(706) = "5649-5656"
aContagem(707) = "5657-5664"
aContagem(708) = "5665-5672"
aContagem(709) = "5673-5680"
aContagem(710) = "5681-5688"
aContagem(711) = "5689-5696"
aContagem(712) = "5697-5704"
aContagem(713) = "5705-5712"
aContagem(714) = "5713-5720"
aContagem(715) = "5721-5728"
aContagem(716) = "5729-5736"
aContagem(717) = "5737-5744"
aContagem(718) = "5745-5752"
aContagem(719) = "5753-5760"
aContagem(720) = "5761-5768"
aContagem(721) = "5769-5776"
aContagem(722) = "5777-5784"
aContagem(723) = "5785-5792"
aContagem(724) = "5793-5800"
aContagem(725) = "5801-5808"
aContagem(726) = "5809-5816"
aContagem(727) = "5817-5824"
aContagem(728) = "5825-5832"
aContagem(729) = "5833-5840"
aContagem(730) = "5841-5848"
aContagem(731) = "5849-5856"
aContagem(732) = "5857-5864"
aContagem(733) = "5865-5872"
aContagem(734) = "5873-5880"
aContagem(735) = "5881-5888"
aContagem(736) = "5889-5896"
aContagem(737) = "5897-5904"
aContagem(738) = "5905-5912"
aContagem(739) = "5913-5920"
aContagem(740) = "5921-5928"
aContagem(741) = "5929-5936"
aContagem(742) = "5937-5944"
aContagem(743) = "5945-5952"
aContagem(744) = "5953-5960"
aContagem(745) = "5961-5968"
aContagem(746) = "5969-5976"
aContagem(747) = "5977-5984"
aContagem(748) = "5985-5992"
aContagem(749) = "5993-6000"
aContagem(750) = "6001-6008"
aContagem(751) = "6009-6016"
aContagem(752) = "6017-6024"
aContagem(753) = "6025-6032"
aContagem(754) = "6033-6040"
aContagem(755) = "6041-6048"
aContagem(756) = "6049-6056"
aContagem(757) = "6057-6064"
aContagem(758) = "6065-6072"
aContagem(759) = "6073-6080"
aContagem(760) = "6081-6088"
aContagem(761) = "6089-6096"
aContagem(762) = "6097-6104"
aContagem(763) = "6105-6112"
aContagem(764) = "6113-6120"
aContagem(765) = "6121-6128"
aContagem(766) = "6129-6136"
aContagem(767) = "6137-6144"
aContagem(768) = "6145-6152"
aContagem(769) = "6153-6160"
aContagem(770) = "6161-6168"
aContagem(771) = "6169-6176"
aContagem(772) = "6177-6184"
aContagem(773) = "6185-6192"
aContagem(774) = "6193-6200"
aContagem(775) = "6201-6208"
aContagem(776) = "6209-6216"
aContagem(777) = "6217-6224"
aContagem(778) = "6225-6232"
aContagem(779) = "6233-6240"
aContagem(780) = "6241-6248"
aContagem(781) = "6249-6256"
aContagem(782) = "6257-6264"
aContagem(783) = "6265-6272"
aContagem(784) = "6273-6280"
aContagem(785) = "6281-6288"
aContagem(786) = "6289-6296"
aContagem(787) = "6297-6304"
aContagem(788) = "6305-6312"
aContagem(789) = "6313-6320"
aContagem(790) = "6321-6328"
aContagem(791) = "6329-6336"
aContagem(792) = "6337-6344"
aContagem(793) = "6345-6352"
aContagem(794) = "6353-6360"
aContagem(795) = "6361-6368"
aContagem(796) = "6369-6376"
aContagem(797) = "6377-6384"
aContagem(798) = "6385-6392"
aContagem(799) = "6393-6400"
aContagem(800) = "6401-6408"
aContagem(801) = "6409-6416"
aContagem(802) = "6417-6424"
aContagem(803) = "6425-6432"
aContagem(804) = "6433-6440"
aContagem(805) = "6441-6448"
aContagem(806) = "6449-6456"
aContagem(807) = "6457-6464"
aContagem(808) = "6465-6472"
aContagem(809) = "6473-6480"
aContagem(810) = "6481-6488"
aContagem(811) = "6489-6496"
aContagem(812) = "6497-6504"
aContagem(813) = "6505-6512"
aContagem(814) = "6513-6520"
aContagem(815) = "6521-6528"
aContagem(816) = "6529-6536"
aContagem(817) = "6537-6544"
aContagem(818) = "6545-6552"
aContagem(819) = "6553-6560"
aContagem(820) = "6561-6568"
aContagem(821) = "6569-6576"
aContagem(822) = "6577-6584"
aContagem(823) = "6585-6592"
aContagem(824) = "6593-6600"
aContagem(825) = "6601-6608"
aContagem(826) = "6609-6616"
aContagem(827) = "6617-6624"
aContagem(828) = "6625-6632"
aContagem(829) = "6633-6640"
aContagem(830) = "6641-6648"
aContagem(831) = "6649-6656"
aContagem(832) = "6657-6664"
aContagem(833) = "6665-6672"
aContagem(834) = "6673-6680"
aContagem(835) = "6681-6688"
aContagem(836) = "6689-6696"
aContagem(837) = "6697-6704"
aContagem(838) = "6705-6712"
aContagem(839) = "6713-6720"
aContagem(840) = "6721-6728"
aContagem(841) = "6729-6736"
aContagem(842) = "6737-6744"
aContagem(843) = "6745-6752"
aContagem(844) = "6753-6760"
aContagem(845) = "6761-6768"
aContagem(846) = "6769-6776"
aContagem(847) = "6777-6784"
aContagem(848) = "6785-6792"
aContagem(849) = "6793-6800"
aContagem(850) = "6801-6808"
aContagem(851) = "6809-6816"
aContagem(852) = "6817-6824"
aContagem(853) = "6825-6832"
aContagem(854) = "6833-6840"
aContagem(855) = "6841-6848"
aContagem(856) = "6849-6856"
aContagem(857) = "6857-6864"
aContagem(858) = "6865-6872"
aContagem(859) = "6873-6880"
aContagem(860) = "6881-6888"
aContagem(861) = "6889-6896"
aContagem(862) = "6897-6904"
aContagem(863) = "6905-6912"

End Function

Attribute VB_Name = "Demanda"
Public sTecla_direita As Boolean

Type ponto
    x As Double
    y As Double
End Type

Private ssetObj_TEXTO As AcadSelectionSet
Private ssetObj As AcadSelectionSet
Private ssetObj_Demanda_CX As AcadSelectionSet

Private pt0(2) As Double
Private pt1(2) As Double
Private pt2(2) As Double
Private iCont As Long


Sub duas_retas()

Dim Line1_inicial As ponto
Dim Line1_Final As ponto
Dim Line2_Inicial As ponto
Dim Line2_Final As ponto
    sSelecao = Format(Now(), "hh:mm:ss")
    'ThisDrawing.
    Set ssetLine1 = ThisDrawing.SelectionSets.Add(sSelecao)
    ssetLine1.SelectOnScreen

    sSelecao = Format(Now(), "hh:mm:ss")
    'ThisDrawing.
    Set ssetLine2 = ThisDrawing.SelectionSets.Add(sSelecao & "_")
    ssetLine2.SelectOnScreen
    Set ssetObj = Nothing
    pto_0 = ssetLine1.Item(0).StartPoint
    pto_1 = ssetLine1.Item(0).EndPoint
    pto_2 = ssetLine2.Item(0).StartPoint
    pto_3 = ssetLine2.Item(0).EndPoint
    
    Line1_inicial.x = pto_0(0)
    Line1_inicial.y = pto_0(1)
    Line1_Final.x = pto_1(0)
    Line1_Final.y = pto_1(1)
    
    Line2_Inicial.x = pto_2(0)
    Line2_Inicial.y = pto_2(1)
    Line2_Final.x = pto_3(0)
    Line2_Final.y = pto_3(1)
    
    Encontrada = Intersect(Line1_inicial, Line1_Final, Line2_Inicial, Line2_Final)
    If Encontrada = True Then MsgBox "Tem interceção"
    
End Sub

'/* ********************************************************************** */
'/*                                                                        */
'/*  Calcula a interseccao entre 2 retas (no plano "XY" Z = 0)             */
'/*                                                                        */
'/* k : ponto inicial da reta 1                                            */
'/* l : ponto final da reta 1                                              */
'/* m : ponto inicial da reta 2                                            */
'/* n : ponto final da reta 2                                              */
'/*                                                                        */
'/* s: valor do parâmetro no ponto de interseção (sobre a reta KL)         */
'/* t: valor do parâmetro no ponto de interseção (sobre a reta MN)         */
'/*                                                                        */
'/* ********************************************************************** */
Function Intersect(k As ponto, l As ponto, m As ponto, n As ponto) As Boolean
Dim Pi As ponto
Dim xMenor As Double
Dim xMaior As Double
Dim yMenor As Double
Dim yMaior As Double

Dim det As Double ' double det;

 det = (n.x - m.x) * (l.y - k.y) - (n.y - m.y) * (l.x - k.x)

 If (det = 0#) Then
    Intersect = False ' return 0 ; // não há intersecção
 Else
  s = ((n.x - m.x) * (m.y - k.y) - (n.y - m.y) * (m.x - k.x)) / det
  t = ((l.x - k.x) * (m.y - k.y) - (l.y - k.y) * (m.x - k.x)) / det
  
 Pi.x = k.x + (l.x - k.x) * s
 Pi.y = k.y + (l.y - k.y) * s

 
 
    If Pi.x < k.x Then
        Intersect = False
    Else
        If m.x > n.x Then
            xMaior = m.x
            xMenor = n.x
        Else
            xMaior = n.x
            xMenor = m.x
        End If
        If m.y > n.y Then
            yMaior = m.y
            yMenor = n.y
        Else
            yMaior = n.y
            yMenor = m.y
        End If
        If Pi.x > xMenor And Pi.x < xMaior And Pi.y > yMenor And Pi.y < yMaior Then
            Intersect = True
        Else
            Intersect = False
        End If
    End If
 End If 'return 1; // há intersecção
End Function

Function Angle_Vetores() As Double
Dim sU As Double
Dim sV As Double
Dim x1 As Double
Dim x2 As Double
Dim y1 As Double
Dim y2 As Double


x1 = (pt1(0) - pt0(0))
x2 = (pt2(0) - pt0(0))
y1 = (pt1(1) - pt0(1))
y2 = (pt2(1) - pt0(1))
sU = Sqr((pt0(0) - pt1(0)) ^ 2 + (pt0(1) - pt1(1)) ^ 2)
sV = Sqr((pt0(0) - pt2(0)) ^ 2 + (pt0(1) - pt2(1)) ^ 2)




Angulo = WorksheetFunction.Acos((x1 * x2 + y1 * y2) / (sU * sV))


Angle_Vetores = Angulo



End Function

Sub Processa_Demanda_Um_a_Um_HP()
        
   sSelecao = Format(Now(), "hh:mm:ss")
    'ThisDrawing.
    Set ssetObj = ThisDrawing.SelectionSets.Add(sSelecao)
    ssetObj.SelectOnScreen
    
    selectALayer "_Demanda", ssetObj_TEXTO 'AQUI ELE FAZ A SELEÇÃO DA LAYER E O TIPO DE TEXTO QUE ELE VAI SOMAR LÁ NA FRENTE
    
    Set ssetObj_Demanda_CX = ThisDrawing.SelectionSets.Add(sSelecao & sLayer & iCont) 'SELECIONAR O BLOCO
    If Err <> 0 Then
        sCont = sCont + 1
        Set ssetObj_Demanda_CX = ThisDrawing.SelectionSets.Add(sSelecao & sLayer & iCont & "_")
    End If
   Dim filterType As Variant
   Dim filterData As Variant
   Dim p1(0 To 2) As Double
   Dim p2(0 To 2) As Double
  
   Dim grpCode(0) As Integer
   grpCode(0) = 2
   filterType = grpCode
   Dim grpValue(0) As Variant
   grpValue(0) = "BR_CTO*" 'AQUI ELE SELECIONA O NOME DO BLOCO
   filterData = grpValue
   
   ssetObj_Demanda_CX.Select acSelectionSetAll, p1, p2, filterType, filterData 'ESSE AQUI ELE USA PARA SELECIONAR O BLOCO
    
    
    
    For I = 0 To ssetObj.Count - 1
        If ssetObj.Item(I).ObjectName = "AcDbPolyline" Then
            fCalcula_HP (I)
        End If
    Next

    Set ssetObj = Nothing
    Set ssetObj_TEXTO = Nothing
    Set ssetObj_Demanda_CX = Nothing
End Sub


Sub Processa_Demanda_Um_a_Um_texto_rosa()
        
   sSelecao = Format(Now(), "hh:mm:ss")
    'ThisDrawing.
    Set ssetObj = ThisDrawing.SelectionSets.Add(sSelecao)
    ssetObj.SelectOnScreen
    
    selectALayer "_DEMANDA", ssetObj_TEXTO 'aqui ele faz a seleceção do objeto pela layer e o tipo dele
    
    For I = 0 To ssetObj.Count - 1
        If ssetObj.Item(I).ObjectName = "AcDbPolyline" Then
            fCalcula_ (I)
        End If
    Next

    Set ssetObj = Nothing
    Set ssetObj_TEXTO = Nothing
    Set ssetObj_Demanda_CX = Nothing
    
End Sub


Function fCalcula_(n As Long) ' AQUI ELE USAR ESSE "n" PARA NUMERAR O NUMERO DO fCalcular
Dim xMaior As Double
Dim xMenor As Double
Dim yMaior As Double
Dim yMenor As Double
Dim iValor As Double
Dim Poly As AcadLWPolyline
Dim pt_StartPoint(2) As Double
Dim pt_EndPoint(2) As Double
Dim pt_Next_Point(2) As Double
Dim iAngulo As Double

Dim iIntercect As Long
Dim sBloco As String
sBloco = "C:\PROGRAMA\Demanda(1).dwg" 'mudar o local do bloco para fazer funcionar

'sBloco = "D:\Users\wesley\Ondrive\OneDrive\Documentos\Trabalhos\JSX\Demanda.dwg"
Dim Reta1_inicial As ponto
Dim Reta1_Final As ponto
Dim Reta2_Inicial As ponto
Dim Reta2_Final As ponto

iValor = 0



    'sSelecao = Format(Now(), "hh:mm:ss")
    'ThisDrawing.
    'Set ssetObj = ThisDrawing.SelectionSets.Add(sSelecao)
    'ssetObj.SelectOnScreen
    

    Set Poly = ssetObj.Item(n)
    xMaior = Poly.Coordinates(0)
    xMenor = Poly.Coordinates(0)
    yMaior = Poly.Coordinates(1)
    yMenor = Poly.Coordinates(1)
    Bound = UBound(Poly.Coordinates)
           
           x = 0
           y = 1
    For I = 0 To Bound / 2
        If Poly.Coordinates(x) > xMaior Then
            xMaior = Poly.Coordinates(x)
        ElseIf Poly.Coordinates(x) < xMenor Then
            xMenor = Poly.Coordinates(x)
        End If
        If Poly.Coordinates(y) > yMaior Then
            yMaior = Poly.Coordinates(y)
        ElseIf Poly.Coordinates(y) < yMenor Then
            yMenor = Poly.Coordinates(y)
        End If
        'MsgBox "X= " & Poly.Coordinates(x) & "  Y= " & Poly.Coordinates(y)
        If Err Then Err.Clear
        
        x = x + 2
        y = y + 2
        
    Next
    pt0(0) = xMenor
    pt0(1) = yMenor
    pt1(0) = xMaior
    pt1(1) = yMenor
    'Set lineObj = ThisDrawing.ModelSpace.AddLine(pt0, pt1)
    
    pt0(0) = xMenor
    pt0(1) = yMaior
    pt1(0) = xMaior
    pt1(1) = yMaior
    'Set lineObj = ThisDrawing.ModelSpace.AddLine(pt0, pt1)
    
    
       ' + : Coordinates :  : Variant/Double(0 to 15) : ViaCabos.conjunto
      '- : InsertionPoint :  : Variant/Double(0 to 2) : ViaCabos.conjunto
      
        
        For II = 0 To ssetObj_TEXTO.Count - 1
        
            pt_ = ssetObj_TEXTO.Item(II).InsertionPoint
            pt_(0) = pt_(0)
            If pt_(0) <= xMaior And pt_(0) >= xMenor And _
                pt_(1) <= yMaior And pt_(1) >= yMenor Then
               
                iAngulo = 0
                pt0(0) = pt_(0)
                pt0(1) = pt_(1)
                pt0(2) = 0
                
                x = 0
                y = 1 '
                Reta1_inicial.x = pt0(0)
                Reta1_inicial.y = pt0(1)
                Reta1_Final.x = xMaior
                Reta1_Final.y = pt0(1)
                pt1(0) = Reta1_Final.x
                pt1(1) = Reta1_Final.y
                    
                iIntercect = 0
                For I = 0 To Bound - 1 Step 2
                    Reta2_Inicial.x = Poly.Coordinates(I)
                    Reta2_Inicial.y = Poly.Coordinates(I + 1)
                    If I = (Bound - 1) Then
                        Reta2_Final.x = Poly.Coordinates(0)
                        Reta2_Final.y = Poly.Coordinates(1)
                    Else
                        Reta2_Final.x = Poly.Coordinates(I + 2)
                        Reta2_Final.y = Poly.Coordinates(I + 3)
                    End If
                    If Intersect(Reta1_inicial, Reta1_Final, Reta2_Inicial, Reta2_Final) = True Then
                        iIntercect = iIntercect + 1
                        pt1(0) = Reta2_Final.x
                        pt1(1) = Reta2_Final.y
                    End If
                Next
                If (iIntercect Mod 2) <> 0 Then
                    pt1(0) = Reta2_Final.x
                    pt1(1) = Reta2_Final.y
         
                    'Set lineObj = ThisDrawing.ModelSpace.AddLine(pt0, pt1)
                    If ssetObj_TEXTO.Item(II).ObjectName = "AcDbText" Then
                        iValor = iValor + Val(ssetObj_TEXTO.Item(II).TextString)
                    End If
                End If
                
                'Stop
      
            End If
                
        Next

'daqui para cima eu já entendi como selecionar o objeto\\\\\\\\\\\\\\\\\\\\\\\\\\\\\\\\\\\\\\\\\\\\\\\\\\\\\\\\\\\\\\\\\\\\\\\\\\\\\\\\\\\\\\\\\\

'daqui para baixo ele já fez outras etapas
    'como inserir o bloco
    
    ''  Insere o bloco com a demanda
    pt0(0) = xMenor + ((xMaior - xMenor) / 2)
    pt0(1) = yMenor + ((yMaior - yMenor) / 2)
    
    
    
    
    bInsereBloco = True
    If bInsereBloco = True Then
        
        Dim blockRefObj As AcadBlockReference
        iAngulo = 0
        sEscala = 1
        Dim insertionPnt(0 To 2) As Double
        insertionPnt(0) = pt0(0): insertionPnt(1) = pt0(1): insertionPnt(2) = 0#
    
    
'funcionol tudo certo até aqui\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\\
        Set blockRefObj = ThisDrawing.ModelSpace.InsertBlock(insertionPnt, sBloco, sEscala, sEscala, sEscala, iAngulo) 'DAQUI PARA BAIXO FIZ A MAGICA DA COR DA DEMANDA E A LAYER
        'COLOQUEI A CONDICIONAL AQUI
             If iValor <= 8.9 Then 'ALTERA DE ACORDO COM A DEMANDA USADA NO PROJETO
                blockRefObj.Layer = "TEXTO_DEMANDA"  'AQUI ESCOLHO A LAYER QUER SERA APLICADA TEXTO
             Else
                blockRefObj.Layer = "TEXTO_DEMANDA_ALTA"  'AQUI ESCOLHO A LAYER QUER SERA APLICADA TEXTO
             End If
        blockRefObj.Update
        Dim varAttributes As Variant
        varAttributes = blockRefObj.GetAttributes
        For II = 0 To UBound(varAttributes)
                 
             If UCase(varAttributes(II).TagString) = "DEMANDA" Then
                 varAttributes(II).TextString = iValor 'AQUI VEM PARAR O VALOR FINAL DA SOMA DO HP
             End If
         Next
    
    
    Else
        
        For II = 0 To ssetObj_Demanda_CX.Count - 1
            If ssetObj_Demanda_CX.Item(II).ObjectName = "AcDbBlockReference" Then
              pt_ = ssetObj_Demanda_CX.Item(II).InsertionPoint
              'InsertionPoint
              If pt_(0) <= xMaior And pt_(0) >= xMenor And _
                  pt_(1) <= yMaior And pt_(1) >= yMenor Then
                 
                  iAngulo = 0
                  pt0(0) = pt_(0)
                  pt0(1) = pt_(1)
                  pt0(2) = 0
                  
                  x = 0
                  y = 1 '
                  Reta1_inicial.x = pt0(0)
                  Reta1_inicial.y = pt0(1)
                  Reta1_Final.x = xMaior
                  Reta1_Final.y = pt0(1)
                  pt1(0) = Reta1_Final.x
                  pt1(1) = Reta1_Final.y
                      
                  iIntercect = 0
                  For I = 0 To Bound - 1 Step 2
                      Reta2_Inicial.x = Poly.Coordinates(I)
                      Reta2_Inicial.y = Poly.Coordinates(I + 1)
                      If I = (Bound - 1) Then
                          Reta2_Final.x = Poly.Coordinates(0)
                          Reta2_Final.y = Poly.Coordinates(1)
                      Else
                          Reta2_Final.x = Poly.Coordinates(I + 2)
                          Reta2_Final.y = Poly.Coordinates(I + 3)
                      End If
                      If Intersect(Reta1_inicial, Reta1_Final, Reta2_Inicial, Reta2_Final) = True Then
                          iIntercect = iIntercect + 1
                          pt1(0) = Reta2_Final.x
                          pt1(1) = Reta2_Final.y
                      End If
                  Next
                  If (iIntercect Mod 2) <> 0 Then
                     
                        varAttributes = ssetObj_Demanda_CX.Item(II).GetAttributes
        
                        For j = 0 To UBound(varAttributes)
                            
                                If UCase(varAttributes(j).TagString) = "DEMANDA" Then
                                    'Stop
                                    varAttributes(j).TextString = iValor
                                End If
                        Next
                      
                  End If
                  
                  'Stop
        
              End If
            End If
        Next
    End If
        
        'MsgBox iValor
    



End Function



Sub Soma_Demanda()
Dim xMaior As Double
Dim xMenor As Double
Dim yMaior As Double
Dim yMenor As Double
Dim iValor As Double
Dim Poly As AcadLWPolyline
Dim pt_StartPoint(2) As Double
Dim pt_EndPoint(2) As Double
Dim pt_Next_Point(2) As Double
Dim iAngulo As Double

Dim iIntercect As Long


Dim Reta1_inicial As ponto
Dim Reta1_Final As ponto
Dim Reta2_Inicial As ponto
Dim Reta2_Final As ponto

iValor = 0



    sSelecao = Format(Now(), "hh:mm:ss")
    'ThisDrawing.
    Set ssetObj = ThisDrawing.SelectionSets.Add(sSelecao)
    ssetObj.SelectOnScreen
    

    selectALayer "DEMANDA", ssetObj_TEXTO
    Set Poly = ssetObj.Item(0)
    xMaior = Poly.Coordinates(0)
    xMenor = Poly.Coordinates(0)
    yMaior = Poly.Coordinates(1)
    yMenor = Poly.Coordinates(1)
    Bound = UBound(Poly.Coordinates)
           
           x = 0
           y = 1
    For I = 0 To Bound / 2
        If Poly.Coordinates(x) > xMaior Then
            xMaior = Poly.Coordinates(x)
        ElseIf Poly.Coordinates(x) < xMenor Then
            xMenor = Poly.Coordinates(x)
        End If
        If Poly.Coordinates(y) > yMaior Then
            yMaior = Poly.Coordinates(y)
        ElseIf Poly.Coordinates(y) < yMenor Then
            yMenor = Poly.Coordinates(y)
        End If
        'MsgBox "X= " & Poly.Coordinates(x) & "  Y= " & Poly.Coordinates(y)
        If Err Then Err.Clear
        
        x = x + 2
        y = y + 2
        
    Next
    pt0(0) = xMenor
    pt0(1) = yMenor
    pt1(0) = xMaior
    pt1(1) = yMenor
    'Set lineObj = ThisDrawing.ModelSpace.AddLine(pt0, pt1)
    
    pt0(0) = xMenor
    pt0(1) = yMaior
    pt1(0) = xMaior
    pt1(1) = yMaior
    'Set lineObj = ThisDrawing.ModelSpace.AddLine(pt0, pt1)
    
    
       ' + : Coordinates :  : Variant/Double(0 to 15) : ViaCabos.conjunto
      '- : InsertionPoint :  : Variant/Double(0 to 2) : ViaCabos.conjunto
      
        
        For II = 0 To ssetObj_TEXTO.Count - 1
        
            pt_ = ssetObj_TEXTO.Item(II).TextAlignmentPoint
            'InsertionPoint
            If pt_(0) <= xMaior And pt_(0) >= xMenor And _
                pt_(1) <= yMaior And pt_(1) >= yMenor Then
               
                iAngulo = 0
                pt0(0) = pt_(0)
                pt0(1) = pt_(1)
                pt0(2) = 0
                
                x = 0
                y = 1 '
                Reta1_inicial.x = pt0(0)
                Reta1_inicial.y = pt0(1)
                Reta1_Final.x = xMaior
                Reta1_Final.y = pt0(1)
                pt1(0) = Reta1_Final.x
                pt1(1) = Reta1_Final.y
                    
                iIntercect = 0
                For I = 0 To Bound - 1 Step 2
                    Reta2_Inicial.x = Poly.Coordinates(I)
                    Reta2_Inicial.y = Poly.Coordinates(I + 1)
                    If I = (Bound - 1) Then
                        Reta2_Final.x = Poly.Coordinates(0)
                        Reta2_Final.y = Poly.Coordinates(1)
                    Else
                        Reta2_Final.x = Poly.Coordinates(I + 2)
                        Reta2_Final.y = Poly.Coordinates(I + 3)
                    End If
                    If Intersect(Reta1_inicial, Reta1_Final, Reta2_Inicial, Reta2_Final) = True Then
                        iIntercect = iIntercect + 1
                        pt1(0) = Reta2_Final.x
                        pt1(1) = Reta2_Final.y
                    End If
                Next
                If (iIntercect Mod 2) <> 0 Then
                    pt1(0) = Reta2_Final.x
                    pt1(1) = Reta2_Final.y
         
                    'Set lineObj = ThisDrawing.ModelSpace.AddLine(pt0, pt1)
                    iValor = iValor + Val(ssetObj_TEXTO.Item(II).TextString)
                End If
                
                'Stop
      
            End If
                
        Next
        MsgBox iValor
    
Set ssetObj = Nothing
Set ssetObj_TEXTO = Nothing

End Sub

Function selectALayer(sLayer As String, sObjeto As Object)
   
   iCont = iCont + 1
   sSelecao = Format(Now(), "hh:mm:ss:mm")
   On Error Resume Next
   Set sObjeto = ThisDrawing.SelectionSets.Add(sSelecao & sLayer & iCont)
    If Err <> 0 Then
        sCont = sCont + 1
        Set sObjeto = ThisDrawing.SelectionSets.Add(sSelecao & sLayer & iCont & "_")
    End If
   Dim filterType As Variant
   Dim filterData As Variant
   Dim p1(0 To 2) As Double
   Dim p2(0 To 2) As Double
  
   Dim grpCode(0) As Integer
   grpCode(0) = 8
   filterType = grpCode
   Dim grpValue(0) As Variant
   grpValue(0) = sLayer
   filterData = grpValue
   
   sObjeto.Select acSelectionSetAll, p1, p2, filterType, filterData
  
   
  
End Function

Sub Attribui_Tags()

Dim stexto As String


sSelecao = Format(Now(), "hh:mm:ss")
Set ssetObj_Origem = ThisDrawing.SelectionSets.Add(sSelecao)
ssetObj_Origem.SelectOnScreen
    

sSelecao = Format(Now(), "hh:mm:ss")
Set ssetObj_Destino = ThisDrawing.SelectionSets.Add(sSelecao)
ssetObj_Destino.SelectOnScreen
If ssetObj_Origem.Item(0).ObjectName = "AcDbBlockReference" Then
    Dim varAttributes_Origem As Variant
    varAttributes_Origem = ssetObj_Origem.Item(0).GetAttributes
    
    For I = 0 To ssetObj_Destino.Count - 1
        
        If ssetObj_Destino.Item(I).ObjectName = "AcDbBlockReference" Then
        ' Get the attributes for the block reference
        
            Dim varAttributes As Variant
            varAttributes = ssetObj_Destino.Item(I).GetAttributes
                
                For II = 0 To UBound(varAttributes)
                    For j = 0 To UBound(varAttributes_Origem)
                        If UCase(varAttributes(II).TagString) = UCase(varAttributes_Origem(j).TagString) Then
                        'Stop
                            If varAttributes_Origem(j).TextString <> "" Then varAttributes(II).TextString = varAttributes_Origem(j).TextString
                        End If
                    Next
                Next
        End If
    Next
Else
    MsgBox "Selecione um bloco com atributo"
End If
Set ssetObj_Origem = Nothing
Set ssetObj_Destino = Nothing

End Sub


Function fCalcula_HP(n As Long)
Dim xMaior As Double
Dim xMenor As Double
Dim yMaior As Double
Dim yMenor As Double
Dim iValor As Double
Dim Poly As AcadLWPolyline
Dim pt_StartPoint(2) As Double
Dim pt_EndPoint(2) As Double
Dim pt_Next_Point(2) As Double
Dim iAngulo As Double

Dim iIntercect As Long
Dim sBloco As String
sBloco = "C:\PROGRAMA\Demanda(1).dwg"

Dim Reta1_inicial As ponto
Dim Reta1_Final As ponto
Dim Reta2_Inicial As ponto
Dim Reta2_Final As ponto

iValor = 0



    'sSelecao = Format(Now(), "hh:mm:ss")
    'ThisDrawing.
    'Set ssetObj = ThisDrawing.SelectionSets.Add(sSelecao)
    'ssetObj.SelectOnScreen
    

    Set Poly = ssetObj.Item(n)
    xMaior = Poly.Coordinates(0)
    xMenor = Poly.Coordinates(0)
    yMaior = Poly.Coordinates(1)
    yMenor = Poly.Coordinates(1)
    Bound = UBound(Poly.Coordinates)
           
           x = 0
           y = 1
    For I = 0 To Bound / 2
        If Poly.Coordinates(x) > xMaior Then
            xMaior = Poly.Coordinates(x)
        ElseIf Poly.Coordinates(x) < xMenor Then
            xMenor = Poly.Coordinates(x)
        End If
        If Poly.Coordinates(y) > yMaior Then
            yMaior = Poly.Coordinates(y)
        ElseIf Poly.Coordinates(y) < yMenor Then
            yMenor = Poly.Coordinates(y)
        End If
        'MsgBox "X= " & Poly.Coordinates(x) & "  Y= " & Poly.Coordinates(y)
        If Err Then Err.Clear
        
        x = x + 2
        y = y + 2
        
    Next
    pt0(0) = xMenor
    pt0(1) = yMenor
    pt1(0) = xMaior
    pt1(1) = yMenor
    'Set lineObj = ThisDrawing.ModelSpace.AddLine(pt0, pt1)
    
    pt0(0) = xMenor
    pt0(1) = yMaior
    pt1(0) = xMaior
    pt1(1) = yMaior
    'Set lineObj = ThisDrawing.ModelSpace.AddLine(pt0, pt1)
    
    
       ' + : Coordinates :  : Variant/Double(0 to 15) : ViaCabos.conjunto
      '- : InsertionPoint :  : Variant/Double(0 to 2) : ViaCabos.conjunto
      
        
        For II = 0 To ssetObj_TEXTO.Count - 1
        
            pt_ = ssetObj_TEXTO.Item(II).InsertionPoint

             If pt_(0) <= xMaior And pt_(0) >= xMenor And _
                pt_(1) <= yMaior And pt_(1) >= yMenor Then
               
                iAngulo = 0
                pt0(0) = pt_(0)
                pt0(1) = pt_(1)
                pt0(2) = 0
                
                x = 0
                y = 1 '
                Reta1_inicial.x = pt0(0)
                Reta1_inicial.y = pt0(1)
                Reta1_Final.x = xMaior
                Reta1_Final.y = pt0(1)
                pt1(0) = Reta1_Final.x
                pt1(1) = Reta1_Final.y
                    
                iIntercect = 0
                For I = 0 To Bound - 1 Step 2
                    Reta2_Inicial.x = Poly.Coordinates(I)
                    Reta2_Inicial.y = Poly.Coordinates(I + 1)
                    If I = (Bound - 1) Then
                        Reta2_Final.x = Poly.Coordinates(0)
                        Reta2_Final.y = Poly.Coordinates(1)
                    Else
                        Reta2_Final.x = Poly.Coordinates(I + 2)
                        Reta2_Final.y = Poly.Coordinates(I + 3)
                    End If
                    If Intersect(Reta1_inicial, Reta1_Final, Reta2_Inicial, Reta2_Final) = True Then
                        iIntercect = iIntercect + 1
                        pt1(0) = Reta2_Final.x
                        pt1(1) = Reta2_Final.y
                    End If
                Next
                If (iIntercect Mod 2) <> 0 Then
                    pt1(0) = Reta2_Final.x
                    pt1(1) = Reta2_Final.y
         
                    'Set lineObj = ThisDrawing.ModelSpace.AddLine(pt0, pt1)
                    If ssetObj_TEXTO.Item(II).ObjectName <> "AcDbBlockReference" Then
                    iValor = iValor + Val(ssetObj_TEXTO.Item(II).TextString)
                    End If
                End If
                
                'Stop
      
            End If
                
        Next

    ''  Insere o bloco com a demanda
    pt0(0) = xMenor + ((xMaior - xMenor) / 2)
    pt0(1) = yMenor + ((yMaior - yMenor) / 2)
    
    bInsereBloco = False
    If bInsereBloco = True Then
'
'        Dim blockRefObj As AcadBlockReference
'        iAngulo = 0
'        sEscala = 1
'        Dim insertionPnt(0 To 2) As Double
'        insertionPnt(0) = pt0(0): insertionPnt(1) = pt0(1): insertionPnt(2) = 0#
'
'        Set blockRefObj = ThisDrawing.ModelSpace.InsertBlock(insertionPnt, sBloco, sEscala, sEscala, sEscala, iAngulo)
'        blockRefObj.Layer = "_Demanda"
'        blockRefObj.Update
'        Dim varAttributes As Variant
'        varAttributes = blockRefObj.GetAttributes
'        For II = 0 To UBound(varAttributes)
'
'             If UCase(varAttributes(II).TagString) = "DEMANDA" Then
'                 varAttributes(II).TextString = iValor
'             End If
'        Next
    
    
    Else
        
        For II = 0 To ssetObj_Demanda_CX.Count - 1
            If ssetObj_Demanda_CX.Item(II).ObjectName = "AcDbBlockReference" Then
              pt_ = ssetObj_Demanda_CX.Item(II).InsertionPoint
              'InsertionPoint
              If pt_(0) <= xMaior And pt_(0) >= xMenor And _
                  pt_(1) <= yMaior And pt_(1) >= yMenor Then
                 
                  iAngulo = 0
                  pt0(0) = pt_(0)
                  pt0(1) = pt_(1)
                  pt0(2) = 0
                  
                  x = 0
                  y = 1 '
                  Reta1_inicial.x = pt0(0)
                  Reta1_inicial.y = pt0(1)
                  Reta1_Final.x = xMaior
                  Reta1_Final.y = pt0(1)
                  pt1(0) = Reta1_Final.x
                  pt1(1) = Reta1_Final.y
                      
                  iIntercect = 0
                  For I = 0 To Bound - 1 Step 2
                      Reta2_Inicial.x = Poly.Coordinates(I)
                      Reta2_Inicial.y = Poly.Coordinates(I + 1)
                      If I = (Bound - 1) Then
                          Reta2_Final.x = Poly.Coordinates(0)
                          Reta2_Final.y = Poly.Coordinates(1)
                      Else
                          Reta2_Final.x = Poly.Coordinates(I + 2)
                          Reta2_Final.y = Poly.Coordinates(I + 3)
                      End If
                      If Intersect(Reta1_inicial, Reta1_Final, Reta2_Inicial, Reta2_Final) = True Then
                          iIntercect = iIntercect + 1
                          pt1(0) = Reta2_Final.x
                          pt1(1) = Reta2_Final.y
                      End If
                  Next
                  If (iIntercect Mod 2) <> 0 Then
                     
                        varAttributes = ssetObj_Demanda_CX.Item(II).GetAttributes
        
                        For j = 0 To UBound(varAttributes)
                            
                                If UCase(varAttributes(j).TagString) = "SP_PRI" Then
                                    'Stop
                                    varAttributes(j).TextString = iValor
                                End If
                        Next
                      
                  End If
                  
                  'Stop
        
              End If
            End If
        Next
    End If
        
        'MsgBox iValor
    



End Function

Sub Processa_Demanda_Um_a_Um_HP_Invertido()
        
   sSelecao = Format(Now(), "hh:mm:ss")
    'ThisDrawing.
    Set ssetObj = ThisDrawing.SelectionSets.Add(sSelecao)
    ssetObj.SelectOnScreen
    
    selectALayer "_Demanda", ssetObj_TEXTO
    
    Set ssetObj_Demanda_CX = ThisDrawing.SelectionSets.Add(sSelecao & sLayer & iCont)
    If Err <> 0 Then
        sCont = sCont + 1
        Set ssetObj_Demanda_CX = ThisDrawing.SelectionSets.Add(sSelecao & sLayer & iCont & "_")
    End If
   Dim filterType As Variant
   Dim filterData As Variant
   Dim p1(0 To 2) As Double
   Dim p2(0 To 2) As Double
  
   Dim grpCode(0) As Integer
   grpCode(0) = 2
   filterType = grpCode
   Dim grpValue(0) As Variant
   grpValue(0) = "BR_CTO*"
   filterData = grpValue
   
   ssetObj_Demanda_CX.Select acSelectionSetAll, p1, p2, filterType, filterData
    
    
    
    For I = 0 To ssetObj.Count - 1
        If ssetObj.Item(I).ObjectName = "AcDbPolyline" Then
            fCalcula_HP_Invertido (I)
        End If
    Next

    Set ssetObj = Nothing
    Set ssetObj_TEXTO = Nothing
    Set ssetObj_Demanda_CX = Nothing
End Sub

Function fCalcula_HP_Invertido(n As Long)
Dim xMaior As Double
Dim xMenor As Double
Dim yMaior As Double
Dim yMenor As Double
Dim iValor As Double
Dim Poly As AcadLWPolyline
Dim pt_StartPoint(2) As Double
Dim pt_EndPoint(2) As Double
Dim pt_Next_Point(2) As Double
Dim iAngulo As Double

Dim iIntercect As Long
Dim sBloco As String
sBloco = "C:\PROGRAMA\Demanda(1).dwg"

Dim Reta1_inicial As ponto
Dim Reta1_Final As ponto
Dim Reta2_Inicial As ponto
Dim Reta2_Final As ponto

iValor = 0



    'sSelecao = Format(Now(), "hh:mm:ss")
    'ThisDrawing.
    'Set ssetObj = ThisDrawing.SelectionSets.Add(sSelecao)
    'ssetObj.SelectOnScreen
    

    Set Poly = ssetObj.Item(n)
    xMaior = Poly.Coordinates(0)
    xMenor = Poly.Coordinates(0)
    yMaior = Poly.Coordinates(1)
    yMenor = Poly.Coordinates(1)
    Bound = UBound(Poly.Coordinates)
           
           x = 0
           y = 1
    For I = 0 To Bound / 2
        If Poly.Coordinates(x) > xMaior Then
            xMaior = Poly.Coordinates(x)
        ElseIf Poly.Coordinates(x) < xMenor Then
            xMenor = Poly.Coordinates(x)
        End If
        If Poly.Coordinates(y) > yMaior Then
            yMaior = Poly.Coordinates(y)
        ElseIf Poly.Coordinates(y) < yMenor Then
            yMenor = Poly.Coordinates(y)
        End If
        'MsgBox "X= " & Poly.Coordinates(x) & "  Y= " & Poly.Coordinates(y)
        If Err Then Err.Clear
        
        x = x + 2
        y = y + 2
        
    Next
    pt0(0) = xMenor
    pt0(1) = yMenor
    pt1(0) = xMaior
    pt1(1) = yMenor
    'Set lineObj = ThisDrawing.ModelSpace.AddLine(pt0, pt1)
    
    pt0(0) = xMenor
    pt0(1) = yMaior
    pt1(0) = xMaior
    pt1(1) = yMaior
    'Set lineObj = ThisDrawing.ModelSpace.AddLine(pt0, pt1)
    
    
       ' + : Coordinates :  : Variant/Double(0 to 15) : ViaCabos.conjunto
      '- : InsertionPoint :  : Variant/Double(0 to 2) : ViaCabos.conjunto
      
        
        For II = 0 To ssetObj_TEXTO.Count - 1
        
            pt_ = ssetObj_TEXTO.Item(II).InsertionPoint
            pt_(0) = pt_(0) * -1
            If pt_(0) <= xMaior And pt_(0) >= xMenor And _
                pt_(1) <= yMaior And pt_(1) >= yMenor Then
               
                iAngulo = 0
                pt0(0) = pt_(0)
                pt0(1) = pt_(1)
                pt0(2) = 0
                
                x = 0
                y = 1 '
                Reta1_inicial.x = pt0(0)
                Reta1_inicial.y = pt0(1)
                Reta1_Final.x = xMaior
                Reta1_Final.y = pt0(1)
                pt1(0) = Reta1_Final.x
                pt1(1) = Reta1_Final.y
                    
                iIntercect = 0
                For I = 0 To Bound - 1 Step 2
                    Reta2_Inicial.x = Poly.Coordinates(I)
                    Reta2_Inicial.y = Poly.Coordinates(I + 1)
                    If I = (Bound - 1) Then
                        Reta2_Final.x = Poly.Coordinates(0)
                        Reta2_Final.y = Poly.Coordinates(1)
                    Else
                        Reta2_Final.x = Poly.Coordinates(I + 2)
                        Reta2_Final.y = Poly.Coordinates(I + 3)
                    End If
                    If Intersect(Reta1_inicial, Reta1_Final, Reta2_Inicial, Reta2_Final) = True Then
                        iIntercect = iIntercect + 1
                        pt1(0) = Reta2_Final.x
                        pt1(1) = Reta2_Final.y
                    End If
                Next
                If (iIntercect Mod 2) <> 0 Then
                    pt1(0) = Reta2_Final.x
                    pt1(1) = Reta2_Final.y
         
                    'Set lineObj = ThisDrawing.ModelSpace.AddLine(pt0, pt1)
                    If ssetObj_TEXTO.Item(II).ObjectName <> "AcDbBlockReference" Then
                    iValor = iValor + Val(ssetObj_TEXTO.Item(II).TextString)
                    End If
                End If
                
                'Stop
      
            End If
                
        Next

    ''  Insere o bloco com a demanda
    pt0(0) = xMenor + ((xMaior - xMenor) / 2)
    pt0(1) = yMenor + ((yMaior - yMenor) / 2)
    
    bInsereBloco = False
    If bInsereBloco = True Then
        
        Dim blockRefObj As AcadBlockReference
        iAngulo = 0
        sEscala = 1
        Dim insertionPnt(0 To 2) As Double
        insertionPnt(0) = pt0(0) * -1: insertionPnt(1) = pt0(1): insertionPnt(2) = 0#
    
        Set blockRefObj = ThisDrawing.ModelSpace.InsertBlock(insertionPnt, sBloco, sEscala, sEscala, sEscala, iAngulo)
        blockRefObj.Layer = "_Demanda"
        blockRefObj.Update
        Dim varAttributes As Variant
        varAttributes = blockRefObj.GetAttributes
        For II = 0 To UBound(varAttributes)
                 
             If UCase(varAttributes(II).TagString) = "DEMANDA" Then
                 varAttributes(II).TextString = iValor
             End If
         Next
    
    
    Else
        
        For II = 0 To ssetObj_Demanda_CX.Count - 1
            If ssetObj_Demanda_CX.Item(II).ObjectName = "AcDbBlockReference" Then
              pt_ = ssetObj_Demanda_CX.Item(II).InsertionPoint
              'InsertionPoint
              pt_(0) = pt_(0) * -1
              If pt_(0) <= xMaior And pt_(0) >= xMenor And _
                  pt_(1) <= yMaior And pt_(1) >= yMenor Then
                 
                  iAngulo = 0
                  pt0(0) = pt_(0)
                  pt0(1) = pt_(1)
                  pt0(2) = 0
                  
                  x = 0
                  y = 1 '
                  Reta1_inicial.x = pt0(0)
                  Reta1_inicial.y = pt0(1)
                  Reta1_Final.x = xMaior
                  Reta1_Final.y = pt0(1)
                  pt1(0) = Reta1_Final.x
                  pt1(1) = Reta1_Final.y
                      
                  iIntercect = 0
                  For I = 0 To Bound - 1 Step 2
                      Reta2_Inicial.x = Poly.Coordinates(I)
                      Reta2_Inicial.y = Poly.Coordinates(I + 1)
                      If I = (Bound - 1) Then
                          Reta2_Final.x = Poly.Coordinates(0)
                          Reta2_Final.y = Poly.Coordinates(1)
                      Else
                          Reta2_Final.x = Poly.Coordinates(I + 2)
                          Reta2_Final.y = Poly.Coordinates(I + 3)
                      End If
                      If Intersect(Reta1_inicial, Reta1_Final, Reta2_Inicial, Reta2_Final) = True Then
                          iIntercect = iIntercect + 1
                          pt1(0) = Reta2_Final.x
                          pt1(1) = Reta2_Final.y
                      End If
                  Next
                  If (iIntercect Mod 2) <> 0 Then
                     
                        varAttributes = ssetObj_Demanda_CX.Item(II).GetAttributes
        
                        For j = 0 To UBound(varAttributes)
                            
                                If UCase(varAttributes(j).TagString) = "SOMA_TOTAL_HP" Then
                                    'Stop
                                    varAttributes(j).TextString = iValor
                                End If
                        Next
                      
                  End If
                  
                  'Stop
        
              End If
            End If
        Next
    End If
        
        'MsgBox iValor
    



End Function


Sub Processa_Demanda_Um_a_Um_Invertido()
        
   sSelecao = Format(Now(), "hh:mm:ss")
    'ThisDrawing.
    Set ssetObj = ThisDrawing.SelectionSets.Add(sSelecao)
    ssetObj.SelectOnScreen
    
    selectALayer "_Demanda", ssetObj_TEXTO
    
    For I = 0 To ssetObj.Count - 1
        If ssetObj.Item(I).ObjectName = "AcDbPolyline" Then
            fCalcula_Invertido (I)
        End If
    Next

    Set ssetObj = Nothing
    Set ssetObj_TEXTO = Nothing
    Set ssetObj_Demanda_CX = Nothing
End Sub



Function fCalcula_Invertido(n As Long)
Dim xMaior As Double
Dim xMenor As Double
Dim yMaior As Double
Dim yMenor As Double
Dim iValor As Double
Dim Poly As AcadLWPolyline
Dim pt_StartPoint(2) As Double
Dim pt_EndPoint(2) As Double
Dim pt_Next_Point(2) As Double
Dim iAngulo As Double

Dim iIntercect As Long
Dim sBloco As String
sBloco = "C:\PROGRAMA\Demanda(1).dwg"
'sBloco = "D:\Users\wesley\Ondrive\OneDrive\Documentos\Trabalhos\JSX\Demanda.dwg"
Dim Reta1_inicial As ponto
Dim Reta1_Final As ponto
Dim Reta2_Inicial As ponto
Dim Reta2_Final As ponto

iValor = 0



    'sSelecao = Format(Now(), "hh:mm:ss")
    'ThisDrawing.
    'Set ssetObj = ThisDrawing.SelectionSets.Add(sSelecao)
    'ssetObj.SelectOnScreen
    

    Set Poly = ssetObj.Item(n)
    xMaior = Poly.Coordinates(0)
    xMenor = Poly.Coordinates(0)
    yMaior = Poly.Coordinates(1)
    yMenor = Poly.Coordinates(1)
    Bound = UBound(Poly.Coordinates)
           
           x = 0
           y = 1
    For I = 0 To Bound / 2
        If Poly.Coordinates(x) > xMaior Then
            xMaior = Poly.Coordinates(x)
        ElseIf Poly.Coordinates(x) < xMenor Then
            xMenor = Poly.Coordinates(x)
        End If
        If Poly.Coordinates(y) > yMaior Then
            yMaior = Poly.Coordinates(y)
        ElseIf Poly.Coordinates(y) < yMenor Then
            yMenor = Poly.Coordinates(y)
        End If
        'MsgBox "X= " & Poly.Coordinates(x) & "  Y= " & Poly.Coordinates(y)
        If Err Then Err.Clear
        
        x = x + 2
        y = y + 2
        
    Next
    pt0(0) = xMenor
    pt0(1) = yMenor
    pt1(0) = xMaior
    pt1(1) = yMenor
    'Set lineObj = ThisDrawing.ModelSpace.AddLine(pt0, pt1)
    
    pt0(0) = xMenor
    pt0(1) = yMaior
    pt1(0) = xMaior
    pt1(1) = yMaior
    'Set lineObj = ThisDrawing.ModelSpace.AddLine(pt0, pt1)
    
    
       ' + : Coordinates :  : Variant/Double(0 to 15) : ViaCabos.conjunto
      '- : InsertionPoint :  : Variant/Double(0 to 2) : ViaCabos.conjunto
      
        
        For II = 0 To ssetObj_TEXTO.Count - 1
        
            pt_ = ssetObj_TEXTO.Item(II).InsertionPoint
            pt_(0) = pt_(0) * -1
            If pt_(0) <= xMaior And pt_(0) >= xMenor And _
                pt_(1) <= yMaior And pt_(1) >= yMenor Then
               
                iAngulo = 0
                pt0(0) = pt_(0)
                pt0(1) = pt_(1)
                pt0(2) = 0
                
                x = 0
                y = 1 '
                Reta1_inicial.x = pt0(0)
                Reta1_inicial.y = pt0(1)
                Reta1_Final.x = xMaior
                Reta1_Final.y = pt0(1)
                pt1(0) = Reta1_Final.x
                pt1(1) = Reta1_Final.y
                    
                iIntercect = 0
                For I = 0 To Bound - 1 Step 2
                    Reta2_Inicial.x = Poly.Coordinates(I)
                    Reta2_Inicial.y = Poly.Coordinates(I + 1)
                    If I = (Bound - 1) Then
                        Reta2_Final.x = Poly.Coordinates(0)
                        Reta2_Final.y = Poly.Coordinates(1)
                    Else
                        Reta2_Final.x = Poly.Coordinates(I + 2)
                        Reta2_Final.y = Poly.Coordinates(I + 3)
                    End If
                    If Intersect(Reta1_inicial, Reta1_Final, Reta2_Inicial, Reta2_Final) = True Then
                        iIntercect = iIntercect + 1
                        pt1(0) = Reta2_Final.x
                        pt1(1) = Reta2_Final.y
                    End If
                Next
                If (iIntercect Mod 2) <> 0 Then
                    pt1(0) = Reta2_Final.x
                    pt1(1) = Reta2_Final.y
         
                    'Set lineObj = ThisDrawing.ModelSpace.AddLine(pt0, pt1)
                    If ssetObj_TEXTO.Item(II).ObjectName = "AcDbText" Then
                        iValor = iValor + Val(ssetObj_TEXTO.Item(II).TextString)
                    End If
                End If
                
                'Stop
      
            End If
                
        Next

    ''  Insere o bloco com a demanda
    pt0(0) = xMenor + ((xMaior - xMenor) / 2)
    pt0(1) = yMenor + ((yMaior - yMenor) / 2)
    
    bInsereBloco = True
    If bInsereBloco = True Then
        
        Dim blockRefObj As AcadBlockReference
        iAngulo = 0
        sEscala = 1
        Dim insertionPnt(0 To 2) As Double
        insertionPnt(0) = pt0(0) * -1: insertionPnt(1) = pt0(1): insertionPnt(2) = 0#
    
        Set blockRefObj = ThisDrawing.ModelSpace.InsertBlock(insertionPnt, sBloco, sEscala, sEscala, sEscala, iAngulo)
        blockRefObj.Layer = "TEXTO_DEMANDA"
        blockRefObj.Update
        Dim varAttributes As Variant
        varAttributes = blockRefObj.GetAttributes
        For II = 0 To UBound(varAttributes)
                 
             If UCase(varAttributes(II).TagString) = "DEMANDA" Then
                 varAttributes(II).TextString = iValor
             End If
         Next
    
    
    Else
        
        For II = 0 To ssetObj_Demanda_CX.Count - 1
            If ssetObj_Demanda_CX.Item(II).ObjectName = "AcDbBlockReference" Then
              pt_ = ssetObj_Demanda_CX.Item(II).InsertionPoint
              'InsertionPoint
              pt_(0) = pt_(0) * -1
              If pt_(0) <= xMaior And pt_(0) >= xMenor And _
                  pt_(1) <= yMaior And pt_(1) >= yMenor Then
                 
                  iAngulo = 0
                  pt0(0) = pt_(0)
                  pt0(1) = pt_(1)
                  pt0(2) = 0
                  
                  x = 0
                  y = 1 '
                  Reta1_inicial.x = pt0(0)
                  Reta1_inicial.y = pt0(1)
                  Reta1_Final.x = xMaior
                  Reta1_Final.y = pt0(1)
                  pt1(0) = Reta1_Final.x
                  pt1(1) = Reta1_Final.y
                      
                  iIntercect = 0
                  For I = 0 To Bound - 1 Step 2
                      Reta2_Inicial.x = Poly.Coordinates(I)
                      Reta2_Inicial.y = Poly.Coordinates(I + 1)
                      If I = (Bound - 1) Then
                          Reta2_Final.x = Poly.Coordinates(0)
                          Reta2_Final.y = Poly.Coordinates(1)
                      Else
                          Reta2_Final.x = Poly.Coordinates(I + 2)
                          Reta2_Final.y = Poly.Coordinates(I + 3)
                      End If
                      If Intersect(Reta1_inicial, Reta1_Final, Reta2_Inicial, Reta2_Final) = True Then
                          iIntercect = iIntercect + 1
                          pt1(0) = Reta2_Final.x
                          pt1(1) = Reta2_Final.y
                      End If
                  Next
                  If (iIntercect Mod 2) <> 0 Then
                     
                        varAttributes = ssetObj_Demanda_CX.Item(II).GetAttributes
        
                        For j = 0 To UBound(varAttributes)
                            
                                If UCase(varAttributes(j).TagString) = "DEMANDA" Then
                                    'Stop
                                    varAttributes(j).TextString = iValor
                                End If
                        Next
                      
                  End If
                  
                  'Stop
        
              End If
            End If
        Next
    End If
        
        'MsgBox iValor
    



End Function

Attribute VB_Name = "Diversos"
Public sset As AcadSelectionSet
Public point1(0 To 2) As Double
Public point2(0 To 2) As Double
Public location(0 To 2) As Double

Sub Cota_Postes()
Dim iDistanciaCalculada As Double
Dim iDistancia As Double
Dim j As Long


fFiltroLayer "Postes"

For I = 0 To sset.Count - 1
    iDistancia = 99999
    pt1 = sset.Item(I).InsertionPoint
    For II = 0 To sset.Count - 1
        If sset.Item(I).Handle <> sset.Item(II).Handle Then
            pt2 = sset.Item(II).InsertionPoint
            If pt2(0) > pt1(0) Then
                iDistanciaCalculada = getdist(sset.Item(I).InsertionPoint, sset.Item(II).InsertionPoint)
                If iDistancia > iDistanciaCalculada Then
                    j = II
                    iDistancia = iDistanciaCalculada
                End If
            End If
        End If
    Next ' Segunda seleção
    point1(0) = pt1(0)
    point1(1) = pt1(1)
    point1(2) = pt1(2)
    pt2 = sset.Item(j).InsertionPoint
    point2(0) = pt2(0)
    point2(1) = pt2(1)
    point2(2) = pt2(2)
    location(0) = pt1(0)
    location(1) = pt1(1)
    location(2) = pt1(2)
 
    
Next ' primeira seleção


End Sub
Function getdist(pt1, pt2)
Dim oLine As AcadLine
    Set oLine = ThisDrawing.ModelSpace.AddLine(pt1, pt2)
    getdist = oLine.Length
    oLine.Delete
End Function

' https://adndevblog.typepad.com/autocad/2012/07/vba-how-to-setup-selectionset-filters-for-a-block-or-layer.html
Function fFiltroLayer(sLayer As String)

sSelect = Format(Now(), "hh:mm:ss")
Set sset = ThisDrawing.SelectionSets.Add(sSelect)
  
   Dim filterType As Variant
   Dim filterData As Variant
   Dim p1(0 To 2) As Double
   Dim p2(0 To 2) As Double
  
   Dim grpCode(0) As Integer
   grpCode(0) = 8
   filterType = grpCode
   Dim grpValue(0) As Variant
   grpValue(0) = sLayer
   filterData = grpValue
   
   sset.Select acSelectionSetAll, p1, p2, filterType, filterData
  
  
End Function
Sub Attribui_Demanda()



Dim stexto As String


sSelecao = Format(Now(), "hh:mm:ss")
Set ssetObj = ThisDrawing.SelectionSets.Add(sSelecao)
ssetObj.SelectOnScreen
        
Dim varAttributes As Variant
varAttributes = ssetObj.Item(0).GetAttributes

For II = 0 To UBound(varAttributes)
             
     If UCase(varAttributes(II).TagString) = UCase("Demanda") Then
 
         stexto = varAttributes(II).TextString
     End If

Next


For I = 1 To ssetObj.Count - 1
    
    If ssetObj.Item(I).ObjectName = "AcDbBlockReference" Then
    ' Get the attributes for the block reference
    
        
        varAttributes = ssetObj.Item(I).GetAttributes
        
            For II = 0 To UBound(varAttributes)
                
                    If UCase(varAttributes(II).TagString) = UCase("SOMA_TOTAL_HP") Then
                        'Stop
                        varAttributes(II).TextString = stexto
                    End If
               
            Next
    End If
Next
    
Set ssetObj = Nothing

End Sub
Public Sub ColorGreen()

'FINALMENTE EU CONSEGUIR ENCONTRAR UMA FORMA FACIL DE TROCAR A COR OU LAYER DE QUALQUER OBJETO

Dim objSelectionSet As AcadSelectionSet
Dim objDrawingObject As AcadEntity

'choose a selection set name that you only use as temporary storage and 'ensure that it does not currently exist
On Error Resume Next

ThisDrawing.SelectionSets("TempSSet").Delete

Set objSelectionSet = ThisDrawing.SelectionSets.Add("TempSSet")

'ask user to pick entities on the screen

objSelectionSet.SelectOnScreen

For Each objDrawingObject In objSelectionSet
objDrawingObject.color = acGreen
'objDrawingObject.Layer = "RAYNANDO" 'troca por layer muito bom

objDrawingObject.Update

Next
objSelectionSet.Delete

End Sub

Sub chama()
    UserForm1.show
End Sub

Sub SOMA_COTA()


Dim SOMA As Double
Dim soma2 As Double

Dim stexto As String
'Dim stexto2 As String
'Call ColorGreen

sSelecao = Format(Now(), "hh:mm:ss")
Set ssetObj = ThisDrawing.SelectionSets.Add(sSelecao)
ssetObj.SelectOnScreen
        
 

soma2 = 0



For I = 0 To ssetObj.Count - 1 'faz a soma do texto
    
    If ssetObj.Item(I).ObjectName = "AcDbText" Then
    ' Get the attributes for the block reference
    SOMA = ssetObj.Item(I).TextString
    soma2 = soma2 + SOMA
    End If
Next
    
    'atribui o valor ao bloco
    
For I = 0 To ssetObj.Count - 1
    If ssetObj.Item(I).ObjectName = "AcDbBlockReference" Then
    
    
        Dim varAttributes As Variant
        varAttributes = ssetObj.Item(I).GetAttributes 'ele relaciona a variavel com o atributo
        
            For II = 0 To UBound(varAttributes)
                
                    If UCase(varAttributes(II).TagString) = UCase("CL_CABO") Then
                        'Stop
                        varAttributes(II).TextString = soma2 'stexto & "," & stexto2
                    End If
            Next
            
           
           
           
                     'atribui o valor do drop
                        If soma2 > 600 Then
                            MsgBox "Maior que 600!"
                            sDrop = ""
                        ElseIf soma2 >= 490 Then
                            sDrop = "600"
                        ElseIf soma2 >= 390 Then
                            sDrop = "500"
                        ElseIf soma2 >= 290 Then
                            sDrop = "400"
                        ElseIf soma2 >= 190 Then
                            sDrop = "300"
                        ElseIf soma2 >= 140 Then
                            sDrop = "200"
                        ElseIf soma2 >= 90 Then
                            sDrop = "150"
                        ElseIf soma2 >= 1 Then
                            sDrop = "100"
                        End If
            
        'Dim varAttributes As Variant
        varAttributes = ssetObj.Item(I).GetAttributes 'ele relaciona a variavel com o atributo
        
            For II = 0 To UBound(varAttributes)
                
                    If UCase(varAttributes(II).TagString) = UCase("TAMANHO_DROP") Then
                        'Stop
                        varAttributes(II).TextString = sDrop
                    End If
            Next
            
            
    End If
Next


 'ThisDrawing.SendCommand soma2
Set ssetObj = Nothing
'Exit Sub
End Sub
Sub Attribui_logradouro()



Dim stexto As String
Dim stexto2 As String


sSelecao = Format(Now(), "hh:mm:ss")
Set ssetObj = ThisDrawing.SelectionSets.Add(sSelecao)
ssetObj.SelectOnScreen
        
   
stexto = ssetObj.Item(0).TextString

stexto2 = ssetObj.Item(1).TextString


For I = 0 To ssetObj.Count - 1
    
    If ssetObj.Item(I).ObjectName = "AcDbBlockReference" Then
    ' Get the attributes for the block reference
    
        Dim varAttributes As Variant
        varAttributes = ssetObj.Item(I).GetAttributes 'ele relaciona a variavel com o atributo
        
            For II = 0 To UBound(varAttributes)
                
                    If UCase(varAttributes(II).TagString) = UCase("Endereço") Then
                        'Stop
                        varAttributes(II).TextString = stexto & "," & stexto2
                    End If
               
            Next
    End If
Next
    
Set ssetObj = Nothing

End Sub

Sub Preenche_Tags()
Dim sTag As String
Dim sPre As String
Dim sPos As String
Dim iDigitos As Long
Dim nInicial As Long


sSelecao = Format(Now(), "hh:mm:ss") ' criando a variável de seleção
Set ssetObj = ThisDrawing.SelectionSets.Add(sSelecao) ' Atribuindo a variével de seleção
ssetObj.SelectOnScreen ' Aguardo a seleção

nInicial = 0
sTag = "CONTAGEM" 'InputBox("Digite a TAG: ")
sPre = "33-40" 'InputBox("Digite a o Texto Pré: ")
'sPos = InputBox("Digite a o Texto Pós: ")

nInicial = 1 'InputBox("Numero inicial: ", "Primeiro Numero")

'If nInicial > 0 Then
    'iDigitos = InputBox("Quantos Digitos: ")
'End If


For I = 0 To ssetObj.Count - 1

    ' Get the attributes for the block reference
    Dim varAttributes As Variant
    On Error Resume Next
    
    varAttributes = ssetObj.Item(I).GetAttributes
    For II = 0 To UBound(varAttributes)
    
        If UCase(varAttributes(II).TagString) = UCase("CONTAGEM") Then
            If nInicial > 0 Then
            numero_string = ""
                
                'numero_string = "0000000000" & nInicial
                'numero_string = Right(numero_string, iDigitos)
                varAttributes(II).TextString = sPre '& numero_string & sPos
            Else
                varAttributes(II).TextString = sPre & sPos
            End If
                
        End If
    
    
    Next
    If nInicial > 0 Then
        nInicial = nInicial + 1
    End If

Next



Set ssetObj = Nothing

End Sub

Sub Tag_Atribui_Tag()
Dim nAtributosOrigem As Long
Dim nAtributosDestino As Long
Dim stexto As String


sSelecao = Format(Now(), "hh:mm:ss")
Set ssetObj = ThisDrawing.SelectionSets.Add(sSelecao)
ssetObj.SelectOnScreen
bTodosAtributos = MsgBox("Atribui todos as Tags?", vbYesNo)


Dim varAttributes As Variant
Dim varAttributesOrigem As Variant
If bTodosAtributos = 7 Then
    For I = 0 To 0
        If ssetObj.Item(I).ObjectName = "AcDbBlockReference" Then
            varAttributesOrigem = ssetObj.Item(I).GetAttributes
            If UBound(varAttributesOrigem) > 0 Then
                ' Origem
                aTexto = ""
                For II = 0 To UBound(varAttributesOrigem)
                    aTexto = aTexto & II + 1 & "-" & UCase(varAttributesOrigem(II).TagString) & Chr(13)
                Next
                nAtributosOrigem = InputBox(aTexto, "Escolha o Attributo Origem?") - 1
                    
                'Destino
                aTexto = ""
                varAttributes = ssetObj.Item(1).GetAttributes
                If UBound(varAttributes) > 0 Then
                    For II = 0 To UBound(varAttributes)
                        aTexto = aTexto & II + 1 & "-" & UCase(varAttributes(II).TagString) & Chr(13)
                    Next
                    nAtributosDestino = InputBox(aTexto, "Escolha o Attributo Destino?") - 1
                    
                    For j = 1 To ssetObj.Count - 1
                        If ssetObj.Item(j).ObjectName = "AcDbBlockReference" Then
                            varAttributes = ssetObj.Item(j).GetAttributes
                            varAttributes(nAtributosDestino).TextString = varAttributesOrigem(nAtributosOrigem).TextString
                        End If
                    Next
                    
                Else
                    MsgBox "Esse objeto não tem atributos!"
                    Exit For
                End If
            Else
                MsgBox "Esse objeto não tem atributos!"
                Exit For
            End If
        
        Else
            MsgBox "Esse objeto não é um bloco!"
            Exit For
        End If
    Next

Else
    If ssetObj.Item(0).ObjectName = "AcDbBlockReference" Then
        varAttributesOrigem = ssetObj.Item(0).GetAttributes
        If UBound(varAttributesOrigem) > 0 Then
            ' todos os objetos
            For I = 1 To ssetObj.Count - 1
                If ssetObj.Item(I).ObjectName = "AcDbBlockReference" Then
                    varAttributes = ssetObj.Item(I).GetAttributes
                    If UBound(varAttributes) > 0 Then
                        ' Tags dos blocos destinos
                        For II = 0 To UBound(varAttributes)
                            For j = 0 To UBound(varAttributesOrigem)
                                If varAttributesOrigem(j).TagString = varAttributes(II).TagString Then
                                    varAttributes(II).TextString = varAttributesOrigem(j).TextString
                                End If
                            Next
                        Next
                    End If
                End If
            Next
        Else
            MsgBox "Esse objeto não tem atributos!"
            
        End If
    Else
        MsgBox "Esse objeto não é um bloco!"
    End If
End If


Set ssetObj = Nothing


End Sub


Sub Atribui_Texto_TAG()
Dim nAtributos As Long
Dim stexto As String
Dim nFor As Long
Dim bCoord As Boolean
bCoord = False

sSelecao = Format(Now(), "hh:mm:ss")
Set ssetObj = ThisDrawing.SelectionSets.Add(sSelecao)
ssetObj.SelectOnScreen
        
   
If ssetObj.Item(0).ObjectName = "AcDbBlockReference" Then
    stexto = InputBox("Digite o texto!", "Para Texto")
        nFor = 0
Else
    If ssetObj.Item(0).ObjectName = "AcDbText" Then
        stexto = ssetObj.Item(0).TextString
        nFor = 1
    Else
        nFor = 0
    End If
End If

bCoord = MsgBox("Atualiza coordenadas?", vbYesNo)
If stexto <> "" Then
    For I = nFor To nFor
    On Error Resume Next
        If ssetObj.Item(I).ObjectName = "AcDbBlockReference" Then
        ' Get the attributes for the block reference
        
            Dim varAttributes As Variant
            varAttributes = ssetObj.Item(I).GetAttributes
            If UBound(varAttributes) > 0 Then
                aTexto = ""
                For II = 0 To UBound(varAttributes)
                    aTexto = aTexto & II + 1 & "-" & UCase(varAttributes(II).TagString) & Chr(13)
                Next
                nAtributos = InputBox(aTexto, "Escolha o Attributo!") - 1
            Else
                MsgBox "Esse objeto não tem atributos!"
                Exit For
            End If
        Else
            MsgBox "Esse objeto não é um bloco!"
            Exit For
        End If
    Next
    
End If


For I = nFor To ssetObj.Count - 1
    
    If ssetObj.Item(I).ObjectName = "AcDbBlockReference" Then
    ' Get the attributes for the block reference
    varAttributes = ssetObj.Item(I).GetAttributes
    If stexto <> "" Then
        varAttributes(nAtributos).TextString = stexto
    End If
        If bCoord = True Then
        pto = ssetObj.Item(I).InsertionPoint
            For II = 0 To UBound(varAttributes)
                If UCase(varAttributes(II).TagString) = "X" Then
                    varAttributes(II).TextString = "X-" & Format(pto(0), "##,###.##")
                ElseIf UCase(varAttributes(II).TagString) = "Y" Then
                    varAttributes(II).TextString = "Y-" & Format(pto(1), "##,###.##")
                End If
                
            Next
        End If
    End If
Next
    
Set ssetObj = Nothing

End Sub
Sub Tag_Atribui_Tag_SP()
Dim nAtributosOrigem As Long
Dim nAtributosDestino As Long
Dim stexto As String


sSelecao = Format(Now(), "hh:mm:ss")
Set ssetObj = ThisDrawing.SelectionSets.Add(sSelecao)
ssetObj.SelectOnScreen
bTodosAtributos = MsgBox("Atribui todos as Tags?", vbYesNo)


Dim varAttributes As Variant
Dim varAttributesOrigem As Variant
If bTodosAtributos = 7 Then
    For I = 0 To 0
        If ssetObj.Item(I).ObjectName = "AcDbBlockReference" Then
            varAttributesOrigem = ssetObj.Item(I).GetAttributes
            If UBound(varAttributesOrigem) > 0 Then
                ' Origem
                aTexto = ""
                For II = 0 To UBound(varAttributesOrigem)
                    aTexto = aTexto & II + 1 & "-" & UCase(varAttributesOrigem(II).TagString) & Chr(13)
                Next
                nAtributosOrigem = InputBox(aTexto, "Escolha o Attributo Origem?") - 1
                    
                'Destino
                aTexto = ""
                varAttributes = ssetObj.Item(1).GetAttributes
                If UBound(varAttributes) > 0 Then
                    For II = 0 To UBound(varAttributes)
                        aTexto = aTexto & II + 1 & "-" & UCase(varAttributes(II).TagString) & Chr(13)
                    Next
                    nAtributosDestino = InputBox(aTexto, "Escolha o Attributo Destino?") - 1
                    
                    For j = 1 To ssetObj.Count - 1
                        If ssetObj.Item(j).ObjectName = "AcDbBlockReference" Then
                            varAttributes = ssetObj.Item(j).GetAttributes
                            varAttributes(nAtributosDestino).TextString = varAttributesOrigem(nAtributosOrigem).TextString
                        End If
                    Next
                    
                Else
                    MsgBox "Esse objeto não tem atributos!"
                    Exit For
                End If
            Else
                MsgBox "Esse objeto não tem atributos!"
                Exit For
            End If
        
        Else
            MsgBox "Esse objeto não é um bloco!"
            Exit For
        End If
    Next

Else
    If ssetObj.Item(0).ObjectName = "AcDbBlockReference" Then
        varAttributesOrigem = ssetObj.Item(0).GetAttributes
        If UBound(varAttributesOrigem) > 0 Then
            ' todos os objetos
            For I = 1 To ssetObj.Count - 1
                If ssetObj.Item(I).ObjectName = "AcDbBlockReference" Then
                    varAttributes = ssetObj.Item(I).GetAttributes
                    If UBound(varAttributes) > 0 Then
                        ' Tags dos blocos destinos
                        For II = 0 To UBound(varAttributes)
                            For j = 0 To UBound(varAttributesOrigem)
                                If varAttributesOrigem(j).TagString = varAttributes(II).TagString Or _
                                    Left(varAttributesOrigem(j).TagString, 2) = Left(varAttributes(II).TagString, 2) Then
                                    varAttributes(II).TextString = varAttributesOrigem(j).TextString
                                End If
                            Next
                        Next
                    End If
                End If
            Next
        Else
            MsgBox "Esse objeto não tem atributos!"
            
        End If
    Else
        MsgBox "Esse objeto não é um bloco!"
    End If
End If


Set ssetObj = Nothing


End Sub



Sub Preenche_SP()
Dim sTag As String
Dim sPre As String
Dim sPos As String
Dim iDigitos As Long
Dim nInicial As Long


sSelecao = Format(Now(), "hh:mm:ss") ' criando a variável de seleção
Set ssetObj = ThisDrawing.SelectionSets.Add(sSelecao) ' Atribuindo a variével de seleção
ssetObj.SelectOnScreen ' Aguardo a seleção

nInicial = 0
sTag = "SP_PRI"
sPre = InputBox("Digite a SP: ")
'sPos = InputBox("Digite a o Texto Pós: ")

'nInicial = InputBox("Numero inicial: ", "Primeiro Numero")

'If nInicial > 0 Then
  '  iDigitos = InputBox("Quantos Digitos: ")
'End If


For I = 0 To ssetObj.Count - 1

    ' Get the attributes for the block reference
    Dim varAttributes As Variant
    On Error Resume Next
    
    varAttributes = ssetObj.Item(I).GetAttributes
    For II = 0 To UBound(varAttributes)
    
        If UCase(varAttributes(II).TagString) = UCase(sTag) Then
            If nInicial > 0 Then
            numero_string = ""
                
                numero_string = "0000000000" & nInicial
                numero_string = Right(numero_string, iDigitos)
                varAttributes(II).TextString = sPre & numero_string
            Else
                varAttributes(II).TextString = "SP-" & sPre
            End If
                
        End If
    
    
    Next
    If nInicial > 0 Then
        nInicial = nInicial + 1
    End If

Next



Set ssetObj = Nothing

End Sub




Sub Preenche_CTO()
Dim sTag As String
Dim sPre As String
Dim sPos As String
Dim iDigitos As Long
Dim nInicial As Long


sSelecao = Format(Now(), "hh:mm:ss") ' criando a variável de seleção
Set ssetObj = ThisDrawing.SelectionSets.Add(sSelecao) ' Atribuindo a variével de seleção
ssetObj.SelectOnScreen ' Aguardo a seleção

nInicial = 0
sTag = "CTO-90-10"
sTag2 = "CTO-85-15"
sTag3 = "CTO-60/40"
sTag4 = "CTO-70-30"
sTag5 = "CTO-80-20"
sTag6 = "CTO-BALANCEADO"

sPre = "CTO-"
'sPos = InputBox("Digite a o Texto Pós: ")

nInicial = InputBox("Numero inicial: ", "Primeiro Numero")

If nInicial > 0 Then
    iDigitos = InputBox("Quantos Digitos: ")
End If


For I = 0 To ssetObj.Count - 1

    ' Get the attributes for the block reference
    Dim varAttributes As Variant
    On Error Resume Next
    
    varAttributes = ssetObj.Item(I).GetAttributes
    For II = 0 To UBound(varAttributes)
    
        If UCase(varAttributes(II).TagString) = UCase(sTag) Or UCase(varAttributes(II).TagString) = UCase(sTag2) Or UCase(varAttributes(II).TagString) = UCase(sTag3) Or UCase(varAttributes(II).TagString) = UCase(sTag4) Or UCase(varAttributes(II).TagString) = UCase(sTag5) Or UCase(varAttributes(II).TagString) = UCase(sTag6) Then
            If nInicial > 0 Then
            numero_string = ""
                
                numero_string = "0000000000" & nInicial
                numero_string = Right(numero_string, iDigitos)
                varAttributes(II).TextString = sPre & numero_string & sPos
            Else
                varAttributes(II).TextString = sPre & sPos
            End If
                
        End If
    
    
    Next
    If nInicial > 0 Then
        nInicial = nInicial + 1
    End If

Next



Set ssetObj = Nothing

End Sub




Sub Preenche_BR_DROP()
Dim sTag As String
Dim sPre As String
Dim sPos As String
Dim iDigitos As Long
Dim nInicial As Long


sSelecao = Format(Now(), "hh:mm:ss") ' criando a variável de seleção
Set ssetObj = ThisDrawing.SelectionSets.Add(sSelecao) ' Atribuindo a variével de seleção
ssetObj.SelectOnScreen ' Aguardo a seleção

nInicial = 0
sTag = "TR"
sPre = InputBox("Digite SP E CTO: ")
'sPos = InputBox("Digite a o Texto Pós: ")

nInicial = InputBox("Numero inicial: ", "Primeiro Numero")

If nInicial > 0 Then
    iDigitos = InputBox("NUMERO DE DIGITOS: ")
End If


For I = 0 To ssetObj.Count - 1

    ' Get the attributes for the block reference
    Dim varAttributes As Variant
    On Error Resume Next
    
    varAttributes = ssetObj.Item(I).GetAttributes
    For II = 0 To UBound(varAttributes)
    
        If UCase(varAttributes(II).TagString) = UCase(sTag) Then
            If nInicial > 0 Then
            numero_string = ""
                
                numero_string = "0000000000" & nInicial
                numero_string = Right(numero_string, iDigitos)
                varAttributes(II).TextString = "TR03,F" & sPre & numero_string
            Else
                varAttributes(II).TextString = sPre
            End If
                
        End If
    
    
    Next
    If nInicial > 0 Then
        nInicial = nInicial + 1
    End If

Next



Set ssetObj = Nothing

End Sub


Sub SomaDrop()
Dim sSoma As Double
Dim sTagDrop As String
Dim sTagCL As String
Dim sDrop As String
Dim sCL As String
Dim sPreDrop As String
Dim sPosDrop As String
Dim sPreCL As String
Dim sPosCL As String


sTagDrop = "DROP-"   'forma de atribuir variaveis a tag para preencher as variaveis corretas
sTagCL = "Linear"    'forma de atribuir variaveis a tag para preencher as variaveis corretas

sPreDrop = "DROP-"   'forma de atribuir variaveis a tag para preencher as variaveis corretas
sPosDrop = ""
sPreCL = "CL="

sPosCL = ""

 
sSelecao = Format(Now(), "hh:mm:ss") ' criando a variável de seleção
Set ssetObj = ThisDrawing.SelectionSets.Add(sSelecao) ' Atribuindo a variével de seleção
ssetObj.SelectOnScreen ' Aguardo a seleção
 
If ssetObj.Item(0).ObjectName = "AcDbPolyline" Then 'SE O PRIMEIRO BLOCO FOR UMA LINHA
    sSoma = ssetObj.Item(0).Length 'ATRIBUA O LENGTH A VARIAVEL sSOMA
End If

If ssetObj.Item(1).ObjectName = "AcDbBlockReference" Then 'SE O SEGUNDO ITEM SELECIONADO FOR UM BLOCO
    Dim varAttributes As Variant
    varAttributes = ssetObj.Item(1).GetAttributes
     For I = 0 To UBound(varAttributes) 'ELE FAZ UM LOOP USANDO O NUMERO DE VARIAVEIS INTERNAS, ASSIM ELE PASSA POR TODAS E FAZ UM "IF"
           If UCase(varAttributes(I).TagString) Like "CTO-*" Then 'AQUI ELE CAPITURA AS INFORMAÇÕES DA TAG CTO- E ARMAZENA EM UMA VARIAVEL iCTO
               iCTO = varAttributes(I).TextString
           ElseIf UCase(varAttributes(I).TagString) = "SP_PRI" Then 'AQUI ELE CAPITURA AS INFORMAÇÕES DA TAG SP_PRI E ARMAZENA EM UMA VARIAVEL iCTO
               sPRI = varAttributes(I).TextString
           ElseIf UCase(varAttributes(I).TagString) = "FOLHA" Then
               sFolha = varAttributes(I).TextString
           End If
           
        Next
End If

If ssetObj.Item(2).ObjectName = "AcDbBlockReference" Then
    Set varAttributes = Nothing
    varAttributes = ssetObj.Item(2).GetAttributes
    
    
    'If MsgBox("Reserva Fusão?", vbYesNo) = vbYes Then
    '    reserva = InputBox("Valor de Arranque:") + 2.5
    'Else
    '    reserva = 5
    'End If
    
    sSoma = sSoma + RESERVA
    
    ' 100m entre 1-95
    ' 150 entre 96-145
    ' 200 entre 146-195
    ' 300 entre 196-295
    ' 400 entre 296-395
    ' 500 entre 396-495
    ' 600 entre 496-600
    
    sDrop = ""
    
    If sSoma > 589 Then         'calculo do drop de acordo com cl do bloco branco
        MsgBox "Maior que 600!"                       ' //
        sDrop = ""
    ElseIf sSoma >= 490 Then                          ' //
        sDrop = "600"                                 ' //
    ElseIf sSoma >= 390 Then
        sDrop = "500"
    ElseIf sSoma >= 290 Then
        sDrop = "400"
    ElseIf sSoma >= 190 Then
        sDrop = "300"
    ElseIf sSoma >= 140 Then
        sDrop = "200"
    ElseIf sSoma >= 90 Then
        sDrop = "150"
    ElseIf sSoma >= 0 Then      'calculo do drop de acordo com cl do bloco branco
        sDrop = "100"
    End If
    If sDrop <> "" Then
            sLayer = "P_DROP-" & sDrop & "_txt"
            'ssetObj.Item(0).Layer = sLayer
           sDrop = sPreDrop & sDrop & sPosDrop
           sCL = sPreCL & Int(sSoma) & sPosCL
        
        For I = 0 To UBound(varAttributes)
           If UCase(varAttributes(I).TagString) = UCase(sTagDrop) Then
               varAttributes(I).TextString = sDrop                      'aqui ele esta atribuindo o valor da variavel sDrop a tag drop do bloco branco
           ElseIf UCase(varAttributes(I).TagString) = UCase(sTagCL) Then
               varAttributes(I).TextString = sCL                        'aqui ele esta atribuindo o valor da variavel sCl a tag CL do bloco branco
           ElseIf UCase(varAttributes(I).TagString) = UCase("TR") Then
            iSP = Val(Replace(sPRI, "SP-", ""))                         'aqui ele esta pegando o numero da sp multiplicando por 8 e subtraindo 7 para descobrir o valor da cto balanceada
            iiCTO = (iSP * 8) - 7
               varAttributes(I).TextString = "TR02,F" & Replace(sPRI, "SP-", "") & "/" & iiCTO & "-" & Replace(iCTO, "CTO-", "") '(Replace) faz a substituição do texto por outro ou nada
           ElseIf UCase(varAttributes(I).TagString) = UCase("FOLHA") Then
               varAttributes(I).TextString = sFolha                     'aqui ele esta atribuindo o valor da variavel sFolha a tag folha do bloco branco
           End If
           
        Next
    End If
Else
    MsgBox "O primeiro objeto tem que ser o bloco"
End If

 
Set ssetObj = Nothing

End Sub




Sub Preenche_CTO_SP_v2()
Dim sTag As String
Dim sPre As String
Dim sPos As String
Dim iDigitos As Long
Dim nInicial As Long
Dim nINsp As Long
Dim nCto As Long

sSelecao = Format(Now(), "hh:mm:ss") ' criando a variável de seleção
Set ssetObj = ThisDrawing.SelectionSets.Add(sSelecao) ' Atribuindo a variével de seleção
ssetObj.SelectOnScreen ' Aguardo a seleção

nInicial = 0
sTag = "CTO-90-10"
sTag2 = "CTO-85-15"
sTag3 = "CTO-60/40"
sTag4 = "CTO-70-30"
sTag5 = "CTO-80-20"
sTag6 = "CTO-BALANCEADO"
sTagsp = "SP_PRI"

sPre = "CTO-"
'sPos = InputBox("Digite a o Texto Pós: ")

nInicial = InputBox("Digite a sp: ")
    nINsp = nInicial

If nInicial > 0 Then
    nCto = nInicial * 8 'mantive o numero da primeira sp
    iDigitos = InputBox("Quantos Digitos: ")
End If


For I = 0 To ssetObj.Count - 1

    ' Get the attributes for the block reference
    Dim varAttributes As Variant
    On Error Resume Next
    
    varAttributes = ssetObj.Item(I).GetAttributes
    For II = 0 To UBound(varAttributes)
    
        If UCase(varAttributes(II).TagString) = UCase(sTag) Or UCase(varAttributes(II).TagString) = UCase(sTag2) Or UCase(varAttributes(II).TagString) = UCase(sTag3) Or UCase(varAttributes(II).TagString) = UCase(sTag4) Or UCase(varAttributes(II).TagString) = UCase(sTag5) Or UCase(varAttributes(II).TagString) = UCase(sTag6) Then
            If nInicial > 0 Then
            numero_string = ""
                
                numero_string = "0000000000" & nCto
                numero_string = Right(numero_string, iDigitos)
                varAttributes(II).TextString = sPre & numero_string & sPos
                
            Else
                varAttributes(II).TextString = "SP///" & sPre
            End If
                
        End If
        
       If UCase(varAttributes(II).TagString) = UCase(sTagsp) Then
             varAttributes(II).TextString = "SP-" & nINsp
             End If
             
    
    Next
    If nInicial > 0 Then
        nCto = nCto - 1 'contagem inversa
    End If

Next



Set ssetObj = Nothing

End Sub





Sub Attribui_FOLHA()



Dim stexto As String


sSelecao = Format(Now(), "hh:mm:ss")
Set ssetObj = ThisDrawing.SelectionSets.Add(sSelecao)
ssetObj.SelectOnScreen
        
   
stexto = ssetObj.Item(0).TextString




For I = 1 To ssetObj.Count - 1
    
    If ssetObj.Item(I).ObjectName = "AcDbBlockReference" Then
    ' Get the attributes for the block reference
    
        Dim varAttributes As Variant
        varAttributes = ssetObj.Item(I).GetAttributes
        
            For II = 0 To UBound(varAttributes)
                
                    If UCase(varAttributes(II).TagString) = UCase("FOLHA") Then
                        'Stop
                        varAttributes(II).TextString = stexto
                    End If
               
            Next
    End If
Next
    
Set ssetObj = Nothing

End Sub


Sub criar_texto()
Dim CADText As acadText
Dim XLnCADText As acadText
Dim NUFI As acadText

Dim Height As Double
Dim QUANTOS As Long
Dim XSEI As Variant
Dim ponto As Variant
Dim InsPoint(0 To 2) As Double
Dim x As Variant
Dim Content1 As String
Dim SP As String
Dim CTOB As Long

 
 Set acad = GetObject(, "AutoCad.Application") 'importante e ainda não sei o que faz
 Set doc = acad.ActiveDocument
 ponto = doc.Utility.GetPoint(, "sele; ")      'SELECIONA O PONTO


Dim RESERVA As Long
RESERVA = InputBox("QUANTAS RESERVAS: ")
QUANTOS = 8
QUANTOS = QUANTOS - RESERVA


Content1 = "CTO-"
Dim RES As String

RES = "RES-"

SP = InputBox("DIGITE A SP: ")


CTOB = SP * 8




 InsPoint(0) = ponto(0) - 13: InsPoint(1) = ponto(1) + 0.54: InsPoint(2) = ponto(2)
    Height = 1.5
 
     
     
    Set NUFI = ThisDrawing.ModelSpace.AddText("TR03,F  " & SP, InsPoint, Height)
    NUFI.Rotation = (0 * 3.14) / 180
    NUFI.StyleName = "Times New Roman" 'ESTILO
    NUFI.ScaleFactor = 0.7 'ESCALA
    NUFI.Layer = "CTO_ 60-40"


 
 
For I = 0 To QUANTOS - 1

    '        X                   Y                   Z
    InsPoint(0) = ponto(0) + XSEI: InsPoint(1) = ponto(1): InsPoint(2) = ponto(2)
    Height = 1.5
 
    
    
     
    Set XLnCADText = ThisDrawing.ModelSpace.AddText(Content1 & CTOB, InsPoint, Height)
    XLnCADText.Rotation = (90 * 3.14) / 180
    XLnCADText.StyleName = "Times New Roman" 'ESTILO
    XLnCADText.ScaleFactor = 0.75 'ESCALA
    XLnCADText.Layer = "CTO_ 60-40"
    
 
    
    If CTOB >= 0 Then
        CTOB = CTOB - 1
      
    End If
     
    If XSEI >= 0 Then
        XSEI = XSEI + 3.32
      
    End If
    
Next
  
  
  For I = 0 To RESERVA - 1

    '        X                   Y                   Z
    InsPoint(0) = ponto(0) + XSEI: InsPoint(1) = ponto(1): InsPoint(2) = ponto(2)
    Height = 1.5
 
    
    
     
    Set XLnCADText = ThisDrawing.ModelSpace.AddText(RES & CTOB, InsPoint, Height)
    XLnCADText.Rotation = (90 * 3.14) / 180
    XLnCADText.StyleName = "Times New Roman" 'ESTILO
    XLnCADText.ScaleFactor = 0.75 'ESCALA
    XLnCADText.Layer = "RESERVA"
    
 
    
    If CTOB >= 0 Then
        CTOB = CTOB - 1
      
    End If
     
    If XSEI >= 0 Then
        XSEI = XSEI + 3.32
      
    End If
    
Next
End Sub


Sub Preenche_TEXTO()
Dim numero_string As String
Dim sPre As String
Dim sPos As String
Dim stexto As String
Dim iDigitos As Long
Dim pulo As Long



sSelecao = Format(Now(), "hh:mm:ss") ' criando a variável de seleção
Set ssetObj = ThisDrawing.SelectionSets.Add(sSelecao) ' Atribuindo a variével de seleção
ssetObj.SelectOnScreen ' Aguardo a seleção


sPre = InputBox("Digite a o Texto Pré: ")
pulo = 1 'InputBox("Digite o pulo: ")
'sPos = InputBox("Digite a o Texto Pós: ")

nInicial = 0
nInicial = InputBox("Numero inicial: ", "Primeiro Numero")
If nInicial > 0 Then
    iDigitos = InputBox("Quantos Digitos: ")
End If


For I = 0 To ssetObj.Count - 1

    
    
        If ssetObj.Item(I).ObjectName = "AcDbText" Then
            If nInicial > 0 Then
            numero_string = ""
                
                numero_string = "0000000000" & nInicial
                numero_string = Right(numero_string, iDigitos)
                ssetObj.Item(I).TextString = sPre & numero_string & sPos
            Else
                ssetObj.Item(I).TextString = sPre & sPos
            End If
                
        End If
    
    If nInicial > 0 Then
        nInicial = nInicial + pulo
    End If

Next



Set ssetObj = Nothing

End Sub




Sub Insere_Bloco_Externo()

Dim sPath_Bloco As String
Dim returnPnt As Variant
Dim blockRef As AcadBlockReference



'criar objeto do cad

Set acad = GetObject(, "AutoCAD.Application")
If Err <> 0 Then
    Set acad = GetObject("AutoCAD.Application")
    acad.Visible = True
    MsgBox "abra o autocad e reinicie essa macro."
    Exit Sub
End If

Set doc = acad.ActiveDocument

' retorna o ponto usando o prompet
returnPnt = doc.Utility.GetPoint(, "selecione um ponto: ")

' caminho para o arquivo dwg
sPath_Bloco = "C:\PROG H\POSTE\new block.dwg"

Set blockRef = doc.ModelSpace.InsertBlock(returnPnt, sPath_Bloco, 1, 1, 1, 0)


Set acad = Nothing

End Sub

Sub Attribui_logradouroV3()


Dim logrado As String

Dim stexto As String
Dim stexto2 As Variant



sSelecao = Format(Now(), "hh:mm:ss")
Set ssetObj = ThisDrawing.SelectionSets.Add(sSelecao)
ssetObj.SelectOnScreen
        
Dim varnume As Variant


 'aqui eu armazenei o nome da rua

varnume = ssetObj.Item(0).GetAttributes 'VARNUME VAI RECEBER OS ATRIBUTOS DO PRIMEIRO ITEM DE SELEÇÃO

For I = 1 To ssetObj.Count - 1
    
    If ssetObj.Item(I).ObjectName = "AcDbBlockReference" Then
    ' Get the attributes for the block reference
    
        Dim varAttributes As Variant
        varAttributes = ssetObj.Item(I).GetAttributes 'ele relaciona a variavel com o atributo
        
            For II = 0 To UBound(varAttributes)
                
                    If UCase(varAttributes(II).TagString) = UCase("Endereço") Then
                        If varAttributes(II).TextString = "" Then
                           
                           varAttributes(II).TextString = stexto2
                        Else
                           
                           stexto = varnume(2).TextString
                           logrado = varAttributes(II).TextString
                           varAttributes(II).TextString = logrado & "," & stexto 'stexto & "," & stexto2
                          
                        End If
                    End If
               
            Next
    End If
Next
    

Set ssetObj = Nothing

End Sub


Sub Attribui_logradouroV2()


Dim logrado As String

Dim stexto As String
'Dim stexto2 As String


sSelecao = Format(Now(), "hh:mm:ss")
Set ssetObj = ThisDrawing.SelectionSets.Add(sSelecao)
ssetObj.SelectOnScreen
        
   
stexto = ssetObj.Item(0).TextString

'stexto2 = ssetObj.Item(1).TextString


For I = 1 To ssetObj.Count - 1
    
    If ssetObj.Item(I).ObjectName = "AcDbBlockReference" Then
    ' Get the attributes for the block reference
    
        Dim varAttributes As Variant
        varAttributes = ssetObj.Item(I).GetAttributes 'ele relaciona a variavel com o atributo
        
            For II = 0 To UBound(varAttributes)
                
                    If UCase(varAttributes(II).TagString) = UCase("Endereço") Then
                        'Stop
                          If varAttributes(II).TextString = "" Then
                           
                           varAttributes(II).TextString = stexto
                          Else
                        logrado = varAttributes(II).TextString
                        varAttributes(II).TextString = logrado & "," & stexto 'stexto & "," & stexto2
                          End If
                    End If
               
            Next
    End If
Next
    
Set ssetObj = Nothing

End Sub




Sub ESQUEMATICO_MANUAL()
  
Dim sPath_Bloco As String
Dim returnPnt As Variant
Dim blockRef As AcadBlockReference
Dim InsPoint(0 To 2) As Double
Dim NUFI As acadText
  
'criar objeto do cad
  
Set acad = GetObject(, "AutoCAD.Application")
If Err <> 0 Then
    Set acad = GetObject("AutoCAD.Application")
    acad.Visible = True
    MsgBox "abra o autocad e reinicie essa macro."
    Exit Sub
End If
  
Set doc = acad.ActiveDocument
  
' retorna o ponto usando o prompet
returnPnt = doc.Utility.GetPoint(, "selecione um ponto: ")
  
' caminho para o arquivo dwg
sPath_Bloco = "C:\PROG H\ESQUEMATICO\BMEDIDA.dwg"
  
Set blockRef = doc.ModelSpace.InsertBlock(returnPnt, sPath_Bloco, 1, 1, 1, 0)
'Set sPath_Bloco = Nothing
Set blockRef = Nothing
  
  
'TEXTO FOLHA
  
  
  
       
    InsPoint(0) = returnPnt(0): InsPoint(1) = returnPnt(1) + 0.44: InsPoint(2) = returnPnt(2)
      
    Set NUFI = ThisDrawing.ModelSpace.AddText("FOLHA RA:XX ", InsPoint, 1.5)
    NUFI.Rotation = (0 * 3.14) / 180
    NUFI.StyleName = "GVTROM" 'ESTILO
    NUFI.ScaleFactor = 0.7 'ESCALA
    NUFI.Layer = "_fibra tronco 2"
    NUFI.Thickness = 0
    NUFI.Lineweight = acLnWt030
     
  
  
Dim RAMAIS As Long
RAMAIS = InputBox("QUANTOS RAMAIS:")
Dim SALTO As Long
SALTO = 0
Dim RES As Long
Dim CTOPONTO(0 To 2) As Double
Dim SALTOCTO As Variant
  
Dim SP As String
Dim CTOB As Long
 
 
SP = InputBox("DIGITE A SP: ")
 
 
For I = 1 To RAMAIS
    'TR03 FX
     InsPoint(0) = returnPnt(0) + 11 + 0.72: InsPoint(1) = returnPnt(1) - 17.74 + 0.9 - SALTO: InsPoint(2) = returnPnt(2)
   
  
      
      
    Set NUFI = ThisDrawing.ModelSpace.AddText("TR03,F  " & SP, InsPoint, 1.5)
    NUFI.Rotation = (0 * 3.14) / 180
    NUFI.StyleName = "Times New Roman" 'ESTILO
    NUFI.ScaleFactor = 0.7 'ESCALA
    NUFI.Layer = "CTO_60-40"
     
     '///////////////////
    RES = InputBox("QUANTAS RESERVAS NO RAMAL " & I & ":")
    InsPoint(0) = returnPnt(0) + 11: InsPoint(1) = returnPnt(1) - 17.74 - SALTO: InsPoint(2) = returnPnt(2)
    sPath_Bloco = "C:\PROG H\ESQUEMATICO\LINHA.dwg"
    Set blockRef = doc.ModelSpace.InsertBlock(InsPoint, sPath_Bloco, 1, 1, 1, 0)
    'SALTO = SALTO + 14.84
    Set blockRef = Nothing
     
     
     
    CTOB = SP * 8
         'LINHA DAS CTOS
        For II = 1 To 8 - RES
                'TEXTO CTO DEU CERTO
                CTOPONTO(0) = returnPnt(0) + 24.05 - 0.1 + SALTOCTO: CTOPONTO(1) = returnPnt(1) - 17.74 + 0.31 - SALTO: CTOPONTO(2) = returnPnt(2)
                 
                 
                Set XLnCADText = ThisDrawing.ModelSpace.AddText("CTO-" & CTOB, CTOPONTO, 1.5)
                XLnCADText.Rotation = (90 * 3.14) / 180
                XLnCADText.StyleName = "Times New Roman" 'ESTILO
                XLnCADText.ScaleFactor = 0.75 'ESCALA
                XLnCADText.Layer = "CTO_60-40"
                 
                CTOB = CTOB - 1
                 
                '///////////////////////////////////////////////
        CTOPONTO(0) = returnPnt(0) + 24.05 + SALTOCTO: CTOPONTO(1) = returnPnt(1) - 17.74 - SALTO: CTOPONTO(2) = returnPnt(2)
        sPath_Bloco = "C:\PROG H\ESQUEMATICO\LINHACTO.dwg"
        Set blockRef = doc.ModelSpace.InsertBlock(CTOPONTO, sPath_Bloco, 1, 1, 1, 0)
        SALTOCTO = SALTOCTO + 3.34
          
        Set blockRef = Nothing
        Next
         
         'LINHA DAS RESERVAS
         For III = 1 To RES
                        'TEXTO RESERVA
                        CTOPONTO(0) = returnPnt(0) + 24.05 - 0.1 + SALTOCTO: CTOPONTO(1) = returnPnt(1) - 17.74 + 0.31 - SALTO: CTOPONTO(2) = returnPnt(2)
                 
                         
                        Set XLnCADText = ThisDrawing.ModelSpace.AddText("RES-" & CTOB, CTOPONTO, 1.5)
                        XLnCADText.Rotation = (90 * 3.14) / 180
                        XLnCADText.StyleName = "Times New Roman" 'ESTILO
                        XLnCADText.ScaleFactor = 0.75 'ESCALA
                        XLnCADText.Layer = "RESERVA"
CTOB = CTOB - 1
                         
                        '////////////////////////////////
                     
        CTOPONTO(0) = returnPnt(0) + 24.05 + SALTOCTO: CTOPONTO(1) = returnPnt(1) - 17.74 - SALTO: CTOPONTO(2) = returnPnt(2)
        sPath_Bloco = "C:\PROG H\ESQUEMATICO\LINHARES.dwg"
        Set blockRef = doc.ModelSpace.InsertBlock(CTOPONTO, sPath_Bloco, 1, 1, 1, 0)
        SALTOCTO = SALTOCTO + 3.34
          
        Set blockRef = Nothing
        Next
         
         
        SP = SP + 1
        SALTOCTO = 0
    SALTO = SALTO + 14.84
Next
  
'DAQUI PARA BAIXO EU VOU PLOTAR A LINHA DAS CTOS E RESERVAS
  
  
  
Set acad = Nothing
  
End Sub

Attribute VB_Name = "Drop"
Sub SomaDrop_Fibrasil()
Dim sSoma As Double
Dim sTagDrop As String
Dim sTagCL As String
Dim sDrop As String
Dim sCL As String
Dim sPreDrop As String
Dim sPosDrop As String
Dim sPreCL As String
Dim sPosCL As String


sTagDrop = "DROP-"
sTagCL = "Linear"

sPreDrop = "DROP="
sPosDrop = ""
sPreCL = "CL="
sPosCL = ""

 
sSelecao = Format(Now(), "hh:mm:ss") ' criando a variável de seleção
Set ssetObj = ThisDrawing.SelectionSets.Add(sSelecao) ' Atribuindo a variével de seleção
ssetObj.SelectOnScreen ' Aguardo a seleção
 
If ssetObj.Item(0).ObjectName = "AcDbPolyline" Then
    sSoma = ssetObj.Item(0).Length
End If


If ssetObj.Item(1).ObjectName = "AcDbBlockReference" Then
    Dim varAttributes As Variant
    varAttributes = ssetObj.Item(1).GetAttributes
    
    
    'If MsgBox("Reserva Fusão?", vbYesNo) = vbYes Then
    '    reserva = InputBox("Valor de Arranque:") + 2.5
    'Else
    '    reserva = 5
    'End If
    
    sSoma = sSoma + RESERVA
    
    ' 100m entre 1-95
    ' 150 entre 96-145
    ' 200 entre 146-195
    ' 300 entre 196-295
    ' 400 entre 296-395
    ' 500 entre 396-495
    ' 600 entre 496-600
    
    sDrop = ""
    
    If sSoma > 600 Then
        MsgBox "Maior que 600!"
        sDrop = ""
    ElseIf sSoma >= 496 Then
        sDrop = "600"
    ElseIf sSoma >= 396 Then
        sDrop = "500"
    ElseIf sSoma >= 296 Then
        sDrop = "400"
    ElseIf sSoma >= 196 Then
        sDrop = "300"
    ElseIf sSoma >= 146 Then
        sDrop = "200"
    ElseIf sSoma >= 96 Then
        sDrop = "150"
    ElseIf sSoma >= 1 Then
        sDrop = "100"
    End If
    If sDrop <> "" Then
            sLayer = "P_DROP-" & sDrop & "_txt"
            'ssetObj.Item(0).Layer = sLayer
           sDrop = sPreDrop & sDrop & sPosDrop
           sCL = sPreCL & sSoma & sPosCL
        
        For I = 0 To UBound(varAttributes)
           If varAttributes(I).TagString = sTagDrop Then
               varAttributes(I).TextString = sDrop
           ElseIf varAttributes(I).TagString = sTagCL Then
               varAttributes(I).TextString = sCL
           End If
           
        Next
    End If
Else
    MsgBox "O primeiro objeto tem que ser o bloco"
End If

 
Set ssetObj = Nothing

End Sub

Attribute VB_Name = "ESQUEMATICO"
Sub ESQUEMATICO_DO_BLOCO()
  
Dim sPath_Bloco As String
Dim returnPnt As Variant
Dim blockRef As AcadBlockReference
Dim InsPoint(0 To 2) As Double
Dim NUFI As acadText
Dim RAMAIS As Long

Dim SP As String
Dim RESERVA As AcadLayer
'criar objeto do cad
'\\\\\\\\\\\\\\\\\\\\\\\\\\\\\\\\\\\\\\\\\\\\\\\\\\\\\\\\\\\\\\\\\\\\\\\\\\\\\\\


    Dim acadApp                 As Object
    Dim acadDoc                 As Object
    Dim acadText                As Object
    Dim acadText2               As Object
    Dim acadText3               As Object
    
    Dim acadColor               As Object
    Dim LastRow                 As Long

    Dim acad As Object
    Dim doc As Object
    
    Set acad = GetObject(, "AutoCAD.Application")
    If Err <> 0 Then
    Set acad = GetObject("AutoCAD.Application")
    acad.Visible = True
    MsgBox "abra o autocad e reinicie essa macro."
    Exit Sub
    End If

    Set doc = acad.ActiveDocument
    
    
    
    'Activate the coordinates sheet and find the last row.
    
        
    'Check if there are coordinates for at least one text message.
    
    
    'Check if AutoCAD application is open. If is not opened create a new instance and make it visible.
    On Error Resume Next
    Set acadApp = GetObject(, "AutoCAD.Application")
    If acadApp Is Nothing Then
        Set acadApp = CreateObject("AutoCAD.Application")
        acadApp.Visible = True
    End If
    
    'Check (again) if there is an AutoCAD object.
    If acadApp Is Nothing Then
        MsgBox "Sorry, it was impossible to start AutoCAD!", vbCritical, "AutoCAD Error"
        Exit Sub
    End If
    On Error GoTo 0
    
    'If there is no active drawing create a new one.
    On Error Resume Next
    Set acadDoc = acadApp.ActiveDocument
    If acadDoc Is Nothing Then
        Set acadDoc = acadApp.Documents.Add
    End If
    On Error GoTo 0

    'Check if the active space is paper space and change it to model space.
    If acadDoc.ActiveSpace = 0 Then '0 = acPaperSpace in early binding
        acadDoc.ActiveSpace = 1     '1 = acModelSpace in early binding
    End If
             
    'Set the AcCmColor object (here acadColor) which represents colors.
    Set acadColor = acadApp.GetInterfaceObject("AutoCAD.AcCmColor." & Left(acadApp.Version, 2))

'\\\\\\\\\\\\\\\\\\\\\\\\\\\\\\\\\\\\\\\\\\\\\\\\\\\\\\\\\\\\\\\\\\\\\\\\\\\\\\\\
Set acad = GetObject(, "AutoCAD.Application")
If Err <> 0 Then
    Set acad = GetObject("AutoCAD.Application")
    acad.Visible = True
    MsgBox "abra o autocad e reinicie essa macro."
    Exit Sub
End If
  
Set doc = acad.ActiveDocument

Set RESERVA = acadDoc.Layers.Add("RESERVA")
                RESERVA.color = 6
  
sSelecao = Format(Now(), "hh:mm:ss")
    Set ssetObj = ThisDrawing.SelectionSets.Add(sSelecao)
    ssetObj.SelectOnScreen
    
    Dim varnume As Variant
    Dim FOLHA As String
    Dim QNT As String
    
    varnume = ssetObj.Item(0).GetAttributes
  
' retorna o ponto usando o prompet
returnPnt = doc.Utility.GetPoint(, "selecione um ponto: ")
  
' caminho para o arquivo dwg
sPath_Bloco = "C:\PROG H\ESQUEMATICO\BMEDIDA.dwg"
  
Set blockRef = doc.ModelSpace.InsertBlock(returnPnt, sPath_Bloco, 1, 1, 1, 0)
'Set sPath_Bloco = Nothing
Set blockRef = Nothing
  
'CHAVE DOS MORTOS

InsPoint(0) = returnPnt(0) + 2.67: InsPoint(1) = returnPnt(1) - 131.61: InsPoint(2) = returnPnt(2)
    sPath_Bloco = "C:\PROG H\ESQUEMATICO\LINHAM.dwg"
    Set blockRef = doc.ModelSpace.InsertBlock(InsPoint, sPath_Bloco, 1, 1, 1, 0)
    'SALTO = SALTO + 14.84
    Set blockRef = Nothing



'\\\\\\\\\\\\\\\\\\\\\\\\\\
  
'TEXTO FOLHA
    'BUSCA A INFORMAÇÃO DA FOLHA
    
    
        If ssetObj.Item(0).ObjectName = "AcDbBlockReference" Then
    ' Get the attributes for the block reference
    
        Dim varAttributes As Variant
        varAttributes = ssetObj.Item(0).GetAttributes 'ele relaciona a variavel com o atributo
        
            For II = 0 To UBound(varAttributes)
                
                    If UCase(varAttributes(II).TagString) = UCase("FOLHA") Then
                        FOLHA = varnume(3).TextString
                    End If
                    
                    If UCase(varAttributes(II).TagString) = UCase("QNT_FIBRA") Then
                        QNT = varnume(6).TextString
                    End If
                    
                    If UCase(varAttributes(II).TagString) = UCase("1º_SP_DA_FOSC") Then
                        SP = varnume(5).TextString
                    End If
                    
                    
               
            Next
    End If
    
    
    InsPoint(0) = returnPnt(0) + 2.67 - 16.9: InsPoint(1) = returnPnt(1) - 131.61 + 0.34: InsPoint(2) = returnPnt(2)
      
    Set NUFI = ThisDrawing.ModelSpace.AddText("RES:TR02:" & QNT & "M", InsPoint, 1.5)
    NUFI.Rotation = (0 * 3.14) / 180
    NUFI.StyleName = "TIMES NEW ROMAN" 'ESTILO
    NUFI.ScaleFactor = 0.7 'ESCALA
    NUFI.Layer = "RESERVA"
    NUFI.Thickness = 0
    NUFI.Lineweight = acLnWt030
    
    '\\\\\\\\\\\\\\\\\\\\\\\\\\\\\\\\
    InsPoint(0) = returnPnt(0): InsPoint(1) = returnPnt(1) + 0.44: InsPoint(2) = returnPnt(2)
      
    Set NUFI = ThisDrawing.ModelSpace.AddText("FOLHA RA:" & FOLHA, InsPoint, 1.5)
    NUFI.Rotation = (0 * 3.14) / 180
    NUFI.StyleName = "GVTROM" 'ESTILO
    NUFI.ScaleFactor = 0.7 'ESCALA
    NUFI.Layer = "_fibra tronco 2"
    NUFI.Thickness = 0
    NUFI.Lineweight = acLnWt030
     
  
  

RAMAIS = QNT
Dim SALTO As Long
SALTO = 0
Dim RES As Long
Dim CTOPONTO(0 To 2) As Double
Dim SALTOCTO As Variant
  

Dim CTOB As Long
 
 
'SP = InputBox("DIGITE A SP: ")
 
 
For I = 1 To RAMAIS
    'TR03 FX
     InsPoint(0) = returnPnt(0) + 11 + 0.72: InsPoint(1) = returnPnt(1) - 17.74 + 0.9 - SALTO: InsPoint(2) = returnPnt(2)
   
  
      
      
    Set NUFI = ThisDrawing.ModelSpace.AddText("TR03,F  " & SP, InsPoint, 1.5)
    NUFI.Rotation = (0 * 3.14) / 180
    NUFI.StyleName = "Times New Roman" 'ESTILO
    NUFI.ScaleFactor = 0.7 'ESCALA
    NUFI.Layer = "CTO_60-40"
     
     '///////////////////
    If varAttributes(I + 5).TextString = "" Then
    RES = 0
    
    Else
     
    RES = varAttributes(I + 5).TextString 'InputBox("QUANTAS RESERVAS NO RAMAL " & I & ":")
    
    End If
    
    InsPoint(0) = returnPnt(0) + 11: InsPoint(1) = returnPnt(1) - 17.74 - SALTO: InsPoint(2) = returnPnt(2)
    sPath_Bloco = "C:\PROG H\ESQUEMATICO\LINHA.dwg"
    Set blockRef = doc.ModelSpace.InsertBlock(InsPoint, sPath_Bloco, 1, 1, 1, 0)
    'SALTO = SALTO + 14.84
    Set blockRef = Nothing
     
    
     
    CTOB = SP * 8
         'LINHA DAS CTOS
        For II = 1 To 8 - RES
                'TEXTO CTO DEU CERTO
                CTOPONTO(0) = returnPnt(0) + 24.05 - 0.1 + SALTOCTO: CTOPONTO(1) = returnPnt(1) - 17.74 + 0.31 - SALTO: CTOPONTO(2) = returnPnt(2)
                 
                 
                Set XLnCADText = ThisDrawing.ModelSpace.AddText("CTO-" & CTOB, CTOPONTO, 1.5)
                XLnCADText.Rotation = (90 * 3.14) / 180
                XLnCADText.StyleName = "Times New Roman" 'ESTILO
                XLnCADText.ScaleFactor = 0.75 'ESCALA
                XLnCADText.Layer = "CTO_60-40"
                 
                CTOB = CTOB - 1
                 
                '///////////////////////////////////////////////
        CTOPONTO(0) = returnPnt(0) + 24.05 + SALTOCTO: CTOPONTO(1) = returnPnt(1) - 17.74 - SALTO: CTOPONTO(2) = returnPnt(2)
        sPath_Bloco = "C:\PROG H\ESQUEMATICO\LINHACTO.dwg"
        Set blockRef = doc.ModelSpace.InsertBlock(CTOPONTO, sPath_Bloco, 1, 1, 1, 0)
        SALTOCTO = SALTOCTO + 3.34
          
        Set blockRef = Nothing
        Next
         
         'LINHA DAS RESERVAS
         For III = 1 To RES
                        'TEXTO RESERVA
                        CTOPONTO(0) = returnPnt(0) + 24.05 - 0.1 + SALTOCTO: CTOPONTO(1) = returnPnt(1) - 17.74 + 0.31 - SALTO: CTOPONTO(2) = returnPnt(2)
                 
                         
                        Set XLnCADText = ThisDrawing.ModelSpace.AddText("RES-" & CTOB, CTOPONTO, 1.5)
                        XLnCADText.Rotation = (90 * 3.14) / 180
                        XLnCADText.StyleName = "Times New Roman" 'ESTILO
                        XLnCADText.ScaleFactor = 0.75 'ESCALA
                        XLnCADText.Layer = "RESERVA"
CTOB = CTOB - 1
                         
                        '////////////////////////////////
                     
        CTOPONTO(0) = returnPnt(0) + 24.05 + SALTOCTO: CTOPONTO(1) = returnPnt(1) - 17.74 - SALTO: CTOPONTO(2) = returnPnt(2)
        sPath_Bloco = "C:\PROG H\ESQUEMATICO\LINHARES.dwg"
        Set blockRef = doc.ModelSpace.InsertBlock(CTOPONTO, sPath_Bloco, 1, 1, 1, 0)
        SALTOCTO = SALTOCTO + 3.34
          
        Set blockRef = Nothing
        Next
         
         
        SP = SP + 1
        SALTOCTO = 0
    SALTO = SALTO + 14.84
Next
  
'DAQUI PARA BAIXO EU VOU PLOTAR A LINHA DAS CTOS E RESERVAS
  
  
  
Set acad = Nothing
  
End Sub

Attribute VB_Name = "Testes"
Sub Zoom()
ZoomBB "1068EE"

End Sub
Public Sub ZoomBB(pHandle As String)
    Dim oEnt As AcadEntity
    Dim vMin As Variant
    Dim vMax As Variant
   
    Set oEnt = ThisDrawing.HandleToObject(pHandle)
   
    oEnt.GetBoundingBox vMin, vMax
   
    ThisDrawing.Application.ZoomWindow vMin, vMax

End Sub

Attribute VB_Name = "ThisDrawing"
Attribute VB_Base = "0{345D3165-3889-4694-AB75-A91A27B217E8}"
Attribute VB_GlobalNameSpace = False
Attribute VB_Creatable = False
Attribute VB_PredeclaredId = True
Attribute VB_Exposed = True
Attribute VB_TemplateDerived = False
Attribute VB_Customizable = True
Private Sub AcadDocument_BeginRightClick(ByVal PickPoint As Variant)
    sTecla_direita = True
End Sub

Attribute VB_Name = "Troca_Blocos"
Private Const sPath_Block = "C:\PROG.02\"

Sub Substitui_Bloco_01()
'Dim sPath_Block As String
Dim sBloco As String
Dim sLayer As String
'sPath_Block = "D:\Users\wesley\Ondrive\OneDrive\Documentos\Trabalhos\JSX\Blocos\"
sBloco = "BR_CTO-90-10.1.dwg"
sLayer = "CTO-90-10.1"

sSelecao = Format(Now(), "hh:mm:ss")
Set ssetObj = ThisDrawing.SelectionSets.Add(sSelecao)
ssetObj.SelectOnScreen

        
For I = 0 To ssetObj.Count - 1
        Dim insertionPnt(0 To 2) As Double
        pto = ssetObj.Item(I).InsertionPoint
        insertionPnt(0) = pto(0)
        insertionPnt(1) = pto(1)
        insertionPnt(2) = pto(2)
        iAngulo = ssetObj.Item(I).Rotation
        xEscale = 1 'ssetObj.Item(i).XScaleFactor
        yEscale = 1 'ssetObj.Item(i).YScaleFactor
        Dim varAttributes_Origem As Variant
        varAttributes_Origem = ssetObj.Item(I).GetAttributes
        
        Dim blockRefObj As AcadBlockReference
                
        Set blockRefObj = ThisDrawing.ModelSpace.InsertBlock(insertionPnt, sPath_Block & sBloco, xEscale, yEscale, 1, iAngulo)
        If ssetObj.Item(I).XScaleFactor = -1 Then
            iAngulo_Mirror = (3.1416145) / 2
            pto(0) = pto(0) + (Math.Cos(iAngulo + iAngulo_Mirror) * 5)
            pto(1) = pto(1) + (Math.Sin(iAngulo + iAngulo_Mirror) * 5)
            pto(2) = pto(2)
            Set RetVal = blockRefObj.Mirror(insertionPnt, pto)
             blockRefObj.Delete
        Else
            Set RetVal = blockRefObj
        End If
        ThisDrawing.Layers.Add sLayer
        RetVal.Layer = sLayer
      
            
        Dim varAttributes As Variant
        varAttributes = RetVal.GetAttributes
        For II = 0 To UBound(varAttributes)
             For j = 0 To UBound(varAttributes_Origem)
                If UCase(varAttributes(II).TagString) = UCase(varAttributes_Origem(j).TagString) Then
                    varAttributes(II).TextString = varAttributes_Origem(j).TextString
                    varAttributes(II).InsertionPoint = varAttributes_Origem(j).InsertionPoint
                End If
             Next
         Next
Next

For I = ssetObj.Count - 1 To 0 Step -1
    ssetObj.Item(I).Delete
Next
Set ssetObj = Nothing
End Sub
Sub Substitui_Bloco_02()
'Dim sPath_Block As String
Dim sBloco As String
Dim sLayer As String
'sPath_Block = "D:\Users\wesley\Ondrive\OneDrive\Documentos\Trabalhos\JSX\Blocos\"
sBloco = "BR_CTO-90-10.2.dwg"
sLayer = "CTO-90-10.2"

sSelecao = Format(Now(), "hh:mm:ss")
Set ssetObj = ThisDrawing.SelectionSets.Add(sSelecao)
ssetObj.SelectOnScreen

        
For I = 0 To ssetObj.Count - 1
        Dim insertionPnt(0 To 2) As Double
        pto = ssetObj.Item(I).InsertionPoint
        insertionPnt(0) = pto(0)
        insertionPnt(1) = pto(1)
        insertionPnt(2) = pto(2)
        iAngulo = ssetObj.Item(I).Rotation
        xEscale = 1 'ssetObj.Item(i).XScaleFactor
        yEscale = 1 'ssetObj.Item(i).YScaleFactor
        Dim varAttributes_Origem As Variant
        varAttributes_Origem = ssetObj.Item(I).GetAttributes
        
        Dim blockRefObj As AcadBlockReference
                
        Set blockRefObj = ThisDrawing.ModelSpace.InsertBlock(insertionPnt, sPath_Block & sBloco, xEscale, yEscale, 1, iAngulo)
        If ssetObj.Item(I).XScaleFactor = -1 Then
            iAngulo_Mirror = (3.1416145) / 2
            pto(0) = pto(0) + (Math.Cos(iAngulo + iAngulo_Mirror) * 5)
            pto(1) = pto(1) + (Math.Sin(iAngulo + iAngulo_Mirror) * 5)
            pto(2) = pto(2)
            Set RetVal = blockRefObj.Mirror(insertionPnt, pto)
             blockRefObj.Delete
        Else
            Set RetVal = blockRefObj
        End If
        ThisDrawing.Layers.Add sLayer
        RetVal.Layer = sLayer
      
            
        Dim varAttributes As Variant
        varAttributes = RetVal.GetAttributes
        For II = 0 To UBound(varAttributes)
             For j = 0 To UBound(varAttributes_Origem)
                If UCase(varAttributes(II).TagString) = UCase(varAttributes_Origem(j).TagString) Then
                    varAttributes(II).TextString = varAttributes_Origem(j).TextString
                    varAttributes(II).InsertionPoint = varAttributes_Origem(j).InsertionPoint
                End If
             Next
         Next
Next

For I = ssetObj.Count - 1 To 0 Step -1
    ssetObj.Item(I).Delete
Next
Set ssetObj = Nothing
End Sub
Sub Substitui_Bloco_03()
'Dim sPath_Block As String
Dim sBloco As String
Dim sLayer As String
'sPath_Block = "D:\Users\wesley\Ondrive\OneDrive\Documentos\Trabalhos\JSX\Blocos\"
sBloco = "BR_CTO-90-10.3.dwg"
sLayer = "CTO-90-10.3"

sSelecao = Format(Now(), "hh:mm:ss")
Set ssetObj = ThisDrawing.SelectionSets.Add(sSelecao)
ssetObj.SelectOnScreen

        
For I = 0 To ssetObj.Count - 1
        Dim insertionPnt(0 To 2) As Double
        pto = ssetObj.Item(I).InsertionPoint
        insertionPnt(0) = pto(0)
        insertionPnt(1) = pto(1)
        insertionPnt(2) = pto(2)
        iAngulo = ssetObj.Item(I).Rotation
        xEscale = 1 'ssetObj.Item(i).XScaleFactor
        yEscale = 1 'ssetObj.Item(i).YScaleFactor
        Dim varAttributes_Origem As Variant
        varAttributes_Origem = ssetObj.Item(I).GetAttributes
        
        Dim blockRefObj As AcadBlockReference
                
        Set blockRefObj = ThisDrawing.ModelSpace.InsertBlock(insertionPnt, sPath_Block & sBloco, xEscale, yEscale, 1, iAngulo)
        If ssetObj.Item(I).XScaleFactor = -1 Then
            iAngulo_Mirror = (3.1416145) / 2
            pto(0) = pto(0) + (Math.Cos(iAngulo + iAngulo_Mirror) * 5)
            pto(1) = pto(1) + (Math.Sin(iAngulo + iAngulo_Mirror) * 5)
            pto(2) = pto(2)
            Set RetVal = blockRefObj.Mirror(insertionPnt, pto)
             blockRefObj.Delete
        Else
            Set RetVal = blockRefObj
        End If
        ThisDrawing.Layers.Add sLayer
        RetVal.Layer = sLayer
      
            
        Dim varAttributes As Variant
        varAttributes = RetVal.GetAttributes
        For II = 0 To UBound(varAttributes)
             For j = 0 To UBound(varAttributes_Origem)
                If UCase(varAttributes(II).TagString) = UCase(varAttributes_Origem(j).TagString) Then
                    varAttributes(II).TextString = varAttributes_Origem(j).TextString
                    varAttributes(II).InsertionPoint = varAttributes_Origem(j).InsertionPoint
                End If
             Next
         Next
Next

For I = ssetObj.Count - 1 To 0 Step -1
    ssetObj.Item(I).Delete
Next
Set ssetObj = Nothing
End Sub

Sub Substitui_Bloco_01_02_03()
'Dim sPath_Block As String
Dim sBloco As String
Dim sLayer As String
'sPath_Block = "D:\Users\wesley\Ondrive\OneDrive\Documentos\Trabalhos\JSX\Blocos\"


sSelecao = Format(Now(), "hh:mm:ss")
Set ssetObj = ThisDrawing.SelectionSets.Add(sSelecao)
ssetObj.SelectOnScreen

        
For I = 0 To ssetObj.Count - 1
        If I = 0 Then
            sBloco = "BR_CTO-90-10.1.dwg"
            sLayer = "CTO-90-10.1"
        ElseIf I = 1 Then
            sBloco = "BR_CTO-90-10.2.dwg"
            sLayer = "CTO-90-10.2"
        Else
            sBloco = "BR_CTO-90-10.3.dwg"
            sLayer = "CTO-90-10.3"
        End If
        Dim insertionPnt(0 To 2) As Double
        pto = ssetObj.Item(I).InsertionPoint
        insertionPnt(0) = pto(0)
        insertionPnt(1) = pto(1)
        insertionPnt(2) = pto(2)
        iAngulo = ssetObj.Item(I).Rotation
        xEscale = 1 'ssetObj.Item(i).XScaleFactor
        yEscale = 1 'ssetObj.Item(i).YScaleFactor
        Dim varAttributes_Origem As Variant
        varAttributes_Origem = ssetObj.Item(I).GetAttributes
        
        Dim blockRefObj As AcadBlockReference
                
        Set blockRefObj = ThisDrawing.ModelSpace.InsertBlock(insertionPnt, sPath_Block & sBloco, xEscale, yEscale, 1, iAngulo)
        If ssetObj.Item(I).XScaleFactor = -1 Then
            iAngulo_Mirror = (3.1416145) / 2
            pto(0) = pto(0) + (Math.Cos(iAngulo + iAngulo_Mirror) * 5)
            pto(1) = pto(1) + (Math.Sin(iAngulo + iAngulo_Mirror) * 5)
            pto(2) = pto(2)
            Set RetVal = blockRefObj.Mirror(insertionPnt, pto)
             blockRefObj.Delete
        Else
            Set RetVal = blockRefObj
        End If
        ThisDrawing.Layers.Add sLayer
        RetVal.Layer = sLayer
      
            
        Dim varAttributes As Variant
        varAttributes = RetVal.GetAttributes
        For II = 0 To UBound(varAttributes)
             For j = 0 To UBound(varAttributes_Origem)
                If UCase(varAttributes(II).TagString) = UCase(varAttributes_Origem(j).TagString) Then
                    varAttributes(II).TextString = varAttributes_Origem(j).TextString
                    varAttributes(II).InsertionPoint = varAttributes_Origem(j).InsertionPoint
                End If
             Next
         Next
Next

For I = ssetObj.Count - 1 To 0 Step -1
    ssetObj.Item(I).Delete
Next
Set ssetObj = Nothing
End Sub

Attribute VB_Name = "UserForm1"
Attribute VB_Base = "0{4E1E3622-42C9-4B65-9386-46704005DDBE}{35121FA7-AAC1-4351-BF08-0E1B09352C7F}"
Attribute VB_GlobalNameSpace = False
Attribute VB_Creatable = False
Attribute VB_PredeclaredId = True
Attribute VB_Exposed = False
Attribute VB_TemplateDerived = False
Attribute VB_Customizable = False
Private Sub CommandButton1_Click()
    Call ColorGreen
End Sub

Private Sub CommandButton2_Click()
    Call SOMA_COTA
End Sub

Private Sub CommandButton3_Click()
    Call ColorGreen
    Call SOMA_COTA
End Sub

Attribute VB_Name = "UserForm2"
Attribute VB_Base = "0{5E2ECDF1-D417-47A9-A77E-91FFAED7CFC7}{3B82B4BC-CF8A-4BE4-8528-5B88F8957A79}"
Attribute VB_GlobalNameSpace = False
Attribute VB_Creatable = False
Attribute VB_PredeclaredId = True
Attribute VB_Exposed = False
Attribute VB_TemplateDerived = False
Attribute VB_Customizable = False
Sub SOMA_CTOS()
    Dim SOMA As Integer
  
    
    SOMA = Val(TextBox1.Text) + Val(TextBox2.Text) + Val(TextBox3.Text) + _
           Val(TextBox4.Text) + Val(TextBox5.Text) + Val(TextBox6.Text) + Val(TextBox7.Text)
    
            
    TextBox8.Value = SOMA
    
End Sub

Private Sub CommandButton1_Click()
    TextBox1.Value = TextBox1.Value + 1
End Sub
Private Sub CommandButton2_Click()
    TextBox2.Value = TextBox2.Value + 1
End Sub
Private Sub CommandButton3_Click()
    TextBox3.Value = TextBox3.Value + 1
End Sub
Private Sub CommandButton4_Click()
    TextBox4.Value = TextBox4.Value + 1
End Sub
Private Sub CommandButton5_Click()
    TextBox5.Value = TextBox5.Value + 1
End Sub
Private Sub CommandButton6_Click()
    TextBox6.Value = TextBox6.Value + 1
End Sub
Private Sub CommandButton7_Click()
    TextBox7.Value = TextBox7.Value + 1
End Sub

Private Sub CommandButton8_Click()
    TextBox1.Value = 0
    TextBox2.Value = 0
    TextBox3.Value = 0
    TextBox4.Value = 0
    TextBox5.Value = 0
    TextBox6.Value = 0
    TextBox7.Value = 0
    
End Sub

Private Sub CommandButton9_Click()
    Call ColorGreen
End Sub

Private Sub TextBox1_Change()
    Call SOMA_CTOS
End Sub
Private Sub TextBox2_Change()
    Call SOMA_CTOS
End Sub
Private Sub TextBox3_Change()
    Call SOMA_CTOS
End Sub
Private Sub TextBox4_Change()
    Call SOMA_CTOS
End Sub
Private Sub TextBox5_Change()
    Call SOMA_CTOS
End Sub
Private Sub TextBox6_Change()
    Call SOMA_CTOS
End Sub
Private Sub TextBox7_Change()
    Call SOMA_CTOS
End Sub




Private Sub UserForm_Click()

End Sub

Attribute VB_Name = "minha_polyline"
Sub poli2()
Dim texto As acadText
Dim plineObj As AcadPolyline
Dim Points() As Double


Dim Start1 As Variant

Dim Finish1 As Variant

On Error GoTo tratar

Start1 = ThisDrawing.Utility.GetPoint(, "select")
Finish1 = ThisDrawing.Utility.GetPoint(Start1, "select point :")

k = 5
ReDim Points(k)
Points(0) = Start1(0): Points(1) = Start1(1): Points(2) = Start1(2)
Points(3) = Finish1(0): Points(4) = Finish1(1): Points(5) = Finish1(2)

Set plineObj = ThisDrawing.ModelSpace.AddPolyline(Points)


Dim meio(0 To 2) As Double


meio(0) = Finish1(0) - (Finish1(0) - Start1(0)) / 2

Set texto = ThisDrawing.ModelSpace.AddText(Round(plineObj.Length, 2), Finish1, 10)
    
    'desenha a polyline\\\\\\\\\\\\\\\\\\\\\\\\\\\\\\
    While Start1(0) <> Finish1(0)
         Start1 = Finish1
         Finish1 = ThisDrawing.Utility.GetPoint(Start1, "select point :")
         plineObj.Delete
         
         
        ReDim Preserve Points(k + 3)
        Points(k + 1) = Finish1(0): Points(k + 2) = Finish1(1): Points(k + 3) = Finish1(2)
        Set plineObj = ThisDrawing.ModelSpace.AddPolyline(Points)
        
        k = k + 3
    Wend


    Exit Sub
tratar:
   Exit Sub
 End Sub
 
Sub poline()
    ' This example creates a polyline in model space.
On Error GoTo tratar
    Dim Start(0 To 2) As Double
    Dim Finish(0 To 2) As Double
    Dim Start1 As Variant
    Dim Finish1 As Variant
    Dim Dline As AcadLine
    Dim Dline2 As AcadLine
    
  Start(0) = 0

  
  Finish(0) = 1

  
    Start1 = ThisDrawing.Utility.GetPoint(, "select")
    Finish1 = ThisDrawing.Utility.GetPoint(Start1, "select point :")
    
    Set Dline = ThisDrawing.ModelSpace.AddLine(Start1, Finish1)
    
    

  'cria varias lines
    While Start(0) <> Finish(0)
         
         Start1 = Finish1
         Finish1 = ThisDrawing.Utility.GetPoint(Start1, "select point :")
         Set Dline2 = ThisDrawing.ModelSpace.AddLine(Start1, Finish1)
         Dline.Delete
        
        Start(0) = Start1(0)
        Finish(0) = Finish1(0)
    Wend
Exit Sub
tratar:
   Exit Sub
    
 End Sub
