Attribute VB_Name = "UserForm1"
Attribute VB_Base = "0{54D2CB64-76A7-4129-9046-4A38452D1F9E}{EC4BEBD8-38E8-43DD-BE86-46926C4706A0}"
Attribute VB_GlobalNameSpace = False
Attribute VB_Creatable = False
Attribute VB_PredeclaredId = True
Attribute VB_Exposed = False
Attribute VB_TemplateDerived = False
Attribute VB_Customizable = False
Private Sub CommandButton1_Click()
    Dim texto As AcadText
    Dim textobox As String
    
    On Error GoTo fechar
    If TextBox1.Value = "" Or TextBox2.Value = "" Then
    
    Else
    'textobox = TextBox1.Value
    
        For i = 0 To TextBox2.Value - 1
            foco.Visible = False
            ponto = ThisDrawing.Utility.GetPoint(, "selecione um ponto")
            Set texto = ThisDrawing.ModelSpace.AddText(TextBox1.Value, ponto, 10)
            foco.Visible = True
            
        Next
    End If
    Exit Sub
fechar:
    Exit Sub
    
End Sub


Private Sub CommandButton2_Click()
    Dim entidade As AcadText
    Dim bloco As AcadText
    
    
    foco.Visible = False
    ThisDrawing.Utility.GetEntity entidade, basePnt, "Select an object"
    
    
    MsgBox "X " & entidade.InsertionPoint(0) & Chr(13) & "y " & entidade.InsertionPoint(1) & Chr(13) & "z " & entidade.InsertionPoint(2)
    
    foco.Visible = True
End Sub

Private Sub TextBox2_Change()
    
End Sub

Private Sub TextBox2_KeyPress(ByVal KeyAscii As MSForms.ReturnInteger)
    TextBox2.MaxLength = 2
    Select Case KeyAscii
    Case 48 To 57
    Case Else: KeyAscii = 0
    End Select
End Sub

Private Sub UserForm_Click()

End Sub
